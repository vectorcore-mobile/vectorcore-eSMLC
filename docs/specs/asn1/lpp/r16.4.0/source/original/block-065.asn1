NR-SSB-Config-r16 ::= SEQUENCE {
nr-PhysCellID-r16NR-PhysCellID-r16,
nr-ARFCN-r16ARFCN-ValueNR-r15,
ss-PBCH-BlockPower-r16INTEGER (-60..50),
halfFrameIndex-r16INTEGER (0..1),
ssb-periodicity-r16ENUMERATED { ms5, ms10, ms20, ms40, ms80, ms160, ...},
ssb-PositionsInBurst-r16CHOICE {
shortBitmap-r16BIT STRING (SIZE (4)),
mediumBitmap-r16BIT STRING (SIZE (8)),
longBitmap-r16BIT STRING (SIZE (64))
}OPTIONAL, --Need OR
ssb-SubcarrierSpacing-r16ENUMERATED {kHz15, kHz30, kHz60, kHz120, kHz240, ...},
sfn-SSB-Offset-r16INTEGER (0..15),
...
}
