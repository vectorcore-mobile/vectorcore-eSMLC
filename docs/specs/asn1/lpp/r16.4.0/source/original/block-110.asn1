GNSS-TimeModelList ::= SEQUENCE (SIZE (1..15)) OF GNSS-TimeModelElement
GNSS-TimeModelElement ::= SEQUENCE {
gnss-TimeModelRefTimeINTEGER (0..65535),
tA0INTEGER (-67108864..67108863),
tA1INTEGER (-4096..4095)OPTIONAL,-- Need ON
tA2INTEGER (-64..63)OPTIONAL,-- Need ON
gnss-TO-IDINTEGER (1..15),
weekNumberINTEGER (0..8191)OPTIONAL,-- Need ON
deltaTINTEGER (-128..127)OPTIONAL,-- Need ON
...
}
