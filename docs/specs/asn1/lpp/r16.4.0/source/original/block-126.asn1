NavModel-BDS-KeplerianSet-r12 ::= SEQUENCE {
bdsAODE-r12INTEGER (0..31),
bdsURAI-r12INTEGER (0..15),
bdsToe-r12INTEGER (0..131071),
bdsAPowerHalf-r12INTEGER (0..4294967295),
bdsE-r12INTEGER (0..4294967295),
bdsW-r12INTEGER (-2147483648..2147483647),
bdsDeltaN-r12INTEGER (-32768..32767),
bdsM0-r12INTEGER (-2147483648..2147483647),
bdsOmega0-r12INTEGER (-2147483648..2147483647),
bdsOmegaDot-r12INTEGER (-8388608..8388607),
bdsI0-r12INTEGER (-2147483648..2147483647),
bdsIDot-r12INTEGER (-8192..8191),
bdsCuc-r12INTEGER (-131072..131071),
bdsCus-r12INTEGER (-131072..131071),
bdsCrc-r12INTEGER (-131072..131071),
bdsCrs-r12INTEGER (-131072..131071),
bdsCic-r12INTEGER (-131072..131071),
bdsCis-r12INTEGER (-131072..131071),
...
}
