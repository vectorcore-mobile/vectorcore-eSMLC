LocationCoordinateTypes ::= SEQUENCE {
ellipsoidPointBOOLEAN,
ellipsoidPointWithUncertaintyCircleBOOLEAN,
ellipsoidPointWithUncertaintyEllipseBOOLEAN,
polygonBOOLEAN,
ellipsoidPointWithAltitudeBOOLEAN,
ellipsoidPointWithAltitudeAndUncertaintyEllipsoidBOOLEAN,
ellipsoidArcBOOLEAN,
...,
[[
highAccuracyEllipsoidPointWithUncertaintyEllipse-r15BOOLEANOPTIONAL,
highAccuracyEllipsoidPointWithAltitudeAndUncertaintyEllipsoid-r15BOOLEANOPTIONAL
]]
}
