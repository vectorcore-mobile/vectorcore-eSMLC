BDS-GridModelParameter-r12 ::= SEQUENCE {
bds-RefTime-r12INTEGER (0..3599),
gridIonList-r12GridIonList-r12,
...
}
GridIonList-r12 ::= SEQUENCE (SIZE (1..320)) OF GridIonElement-r12
GridIonElement-r12 ::= SEQUENCE {
igp-ID-r12INTEGER (1..320),
dt-r12INTEGER (0..511),
givei-r12INTEGER (0..15) ,
...
}
