UTC-ModelSet5-r12 ::= SEQUENCE {
utcA0-r12INTEGER (-2147483648..2147483647),
utcA1-r12INTEGER (-8388608..8388607),
utcDeltaTls-r12INTEGER (-128..127),
utcWNlsf-r12INTEGER (0..255),
utcDN-r12INTEGER (0..255),
utcDeltaTlsf-r12INTEGER (-128..127),
...
}
