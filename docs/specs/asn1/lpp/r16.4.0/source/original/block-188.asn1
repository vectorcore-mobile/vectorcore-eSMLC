GNSS-RTK-MAC-CorrectionDifferencesReq-r15 ::= SEQUENCE {
master-ReferenceStationID-r15GNSS-ReferenceStationID-r15OPTIONAL,
aux-ReferenceStationList-r15AUX-ReferenceStationList-r15OPTIONAL,
linkCombinations-PrefList-r15GNSS-Link-CombinationsList-r15OPTIONAL,
...
}
AUX-ReferenceStationList-r15 ::= SEQUENCE (SIZE (1..32)) OF AUX-ReferenceStationID-Element-r15
AUX-ReferenceStationID-Element-r15 ::= SEQUENCE {
aux-stationID-r15GNSS-ReferenceStationID-r15,
...
}
