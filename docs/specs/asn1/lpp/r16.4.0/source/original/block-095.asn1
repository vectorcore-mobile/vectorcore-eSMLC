GNSS-PeriodicAssistData-r15 ::= SEQUENCE {
gnss-RTK-PeriodicObservations-r15GNSS-PeriodicControlParam-r15OPTIONAL,-- Need ON
glo-RTK-PeriodicBiasInformation-r15GNSS-PeriodicControlParam-r15OPTIONAL,-- Need ON
gnss-RTK-MAC-PeriodicCorrectionDifferences-r15
GNSS-PeriodicControlParam-r15OPTIONAL,-- Need ON
gnss-RTK-PeriodicResiduals-r15GNSS-PeriodicControlParam-r15OPTIONAL,-- Need ON
gnss-RTK-FKP-PeriodicGradients-r15GNSS-PeriodicControlParam-r15OPTIONAL,-- Need ON
gnss-SSR-PeriodicOrbitCorrections-r15
GNSS-PeriodicControlParam-r15OPTIONAL, -- Need ON
gnss-SSR-PeriodicClockCorrections-r15
GNSS-PeriodicControlParam-r15OPTIONAL, -- Need ON
gnss-SSR-PeriodicCodeBias-r15GNSS-PeriodicControlParam-r15OPTIONAL, -- Need ON
...,
[[
gnss-SSR-PeriodicURA-r16GNSS-PeriodicControlParam-r15OPTIONAL,-- Need ON
gnss-SSR-PeriodicPhaseBias-r16GNSS-PeriodicControlParam-r15OPTIONAL, -- Need ON
gnss-SSR-PeriodicSTEC-Correction-r16GNSS-PeriodicControlParam-r15OPTIONAL, -- Need ON
gnss-SSR-PeriodicGriddedCorrection-r16GNSS-PeriodicControlParam-r15OPTIONAL -- Need ON
]]
}
