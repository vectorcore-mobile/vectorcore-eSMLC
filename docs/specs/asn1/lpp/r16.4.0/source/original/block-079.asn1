OTDOA-NeighbourCellInfoListNB-r14 ::= SEQUENCE (SIZE (1..maxCells-r14)) OF
OTDOA-NeighbourCellInfoNB-r14
OTDOA-NeighbourCellInfoNB-r14 ::= SEQUENCE {
physCellIdNB-r14INTEGER (0..503)OPTIONAL,-- Cond NoPRS-AD1
cellGlobalIdNB-r14ECGIOPTIONAL,-- Cond NoPRS-AD2
carrierFreq-r14CarrierFreq-NB-r14OPTIONAL,-- Cond NotSameAsRef1
earfcn-r14ARFCN-ValueEUTRA-r14OPTIONAL,-- Cond Inband
eutra-NumCRS-Ports-r14ENUMERATED {ports-1-or-2, ports-4, ...}
OPTIONAL, -- Cond NotsameAsRef2
otdoa-SIB1-NB-repetitions-r14ENUMERATED { r4, r8, r16 }
OPTIONAL,-- CondNotSameAsRef3
nprsInfo-r14PRS-Info-NB-r14OPTIONAL,-- Cond NotsameAsRef4
nprs-slotNumberOffset-r14INTEGER (0..19)OPTIONAL,-- Cond NotsameAsRef5
nprs-SFN-Offset-r14INTEGER (0..63)OPTIONAL,-- Cond NotsameAsRef6
nprs-SubframeOffset-r14INTEGER (0..1279)OPTIONAL,-- Need OP
expectedRSTD-r14INTEGER (0..16383)OPTIONAL,-- Cond NoPRS-AD3
expectedRSTD-Uncertainty-r14INTEGER (0..1023)OPTIONAL,-- Cond NoPRS-AD3
prsNeighbourCellIndex-r14INTEGER (1..72)OPTIONAL,-- Cond PRS-AD
...,
[[
nprsInfo-Type2-v1470PRS-Info-NB-r14OPTIONAL-- Cond NotSameAsRef4
]],
[[tdd-config-r15TDD-Config-v1520OPTIONAL-- Need ON
]]
}
maxCells-r14INTEGER ::= 72
