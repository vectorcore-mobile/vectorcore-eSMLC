NavModel-BDS-KeplerianSet2-r16 ::= SEQUENCE {
bdsIODE-r16INTEGER (0..255),
bdsToe-r16INTEGER (0..2047),
bdsDeltaA-r16INTEGER (-33554432..33554431),
bdsAdot-r16INTEGER (-16777216..16777216),
bdsDeltaN0-r16INTEGER (-65536..65535),
bdsDeltaN0dot-r16INTEGER (-4194304..4194303),
bdsM0-r16INTEGER (-4294967296..4294967295),
bdsE-r16INTEGER (0..8589934591),
bdsOmega-r16INTEGER (-4294967296..4294967295),
bdsOmega0-r16INTEGER (-4294967296..4294967295),
bdsI0-r16INTEGER (-4294967296..4294967295),
bdsOmegaDot-r16 INTEGER (-262144..262143),
bdsI0Dot-r16INTEGER (-16384..16383),
bdsCuc-r16INTEGER (-1048576..1048575),
bdsCus-r16INTEGER (-1048576..1048575),
bdsCrc-r16INTEGER (-8388608..8388607),
bdsCrs-r16INTEGER (-8388608..8388607),
bdsCic-r16INTEGER (-32768..32767),
bdsCis-r16INTEGER (-32768..32767),
...
}
