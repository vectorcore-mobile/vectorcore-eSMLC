GNSS-SSR-CorrectionPoints-r16 ::= SEQUENCE {
correctionPointSetID-r16INTEGER (0..16383),
correctionPoints-r16CHOICE {
listOfCorrectionPoints-r16GNSS-SSR-ListOfCorrectionPoints-r16,
arrayOfCorrectionPoints-r16GNSS-SSR-ArrayOfCorrectionPoints-r16
},
...
}
GNSS-SSR-ListOfCorrectionPoints-r16 ::= SEQUENCE {
referencePointLatitude-r16INTEGER (-16384..16383),
referencePointLongitude-r16INTEGER (-32768..32767),
relativeLocationsList-r16SEQUENCE (SIZE (0..63)) OF RelativeLocationElement-r16,
...
}
RelativeLocationElement-r16 ::= SEQUENCE {
deltaLatitude-r16INTEGER (-512..511),
deltaLongitude-r16INTEGER (-1024..1023),
...
}
GNSS-SSR-ArrayOfCorrectionPoints-r16 ::=SEQUENCE {
referencePointLatitude-r16INTEGER (-16384..16383),
referencePointLongitude-r16INTEGER (-32768..32767),
numberOfStepsLatitude-r16INTEGER (0..63),
numberOfStepsLongitude-r16INTEGER (0..63),
stepOfLatitude-r16INTEGER (1..511),
stepOfLongitude-r16INTEGER (1..1023),
bitmaskOfGrids-r16BIT STRING (SIZE(64))OPTIONAL,-- Need OP
...
}
