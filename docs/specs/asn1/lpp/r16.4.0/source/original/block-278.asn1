TBS-AssistanceDataList-r14 ::= SEQUENCE {
mbs-AssistanceDataList-r14MBS-AssistanceDataList-r14OPTIONAL,-- Need ON
...
}
MBS-AssistanceDataList-r14 ::= SEQUENCE (SIZE (1..maxMBS-r14)) OF MBS-AssistanceDataElement-r14
MBS-AssistanceDataElement-r14 ::= SEQUENCE {
mbs-AlmanacAssistance-r14MBS-AlmanacAssistance-r14OPTIONAL,-- Need ON
mbs-AcquisitionAssistance-r14MBS-AcquisitionAssistance-r14OPTIONAL,-- Need ON
...
}
