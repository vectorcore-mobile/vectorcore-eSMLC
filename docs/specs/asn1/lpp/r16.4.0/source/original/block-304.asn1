WLAN-AP-Data-r14 ::= SEQUENCE {
wlan-AP-Identifier-r14WLAN-AP-Identifier-r13,
wlan-AP-Location-r14WLAN-AP-Location-r14OPTIONAL,-- Need ON
...
}
WLAN-AP-Location-r14 ::= SEQUENCE {
locationDataLCI-r14LocationDataLCI-r14,
...
}
LocationDataLCI-r14 ::= SEQUENCE {
latitudeUncertainty-r14BIT STRING (SIZE (6)),
latitude-r14BIT STRING (SIZE (34)),
longitudeUncertainty-r14BIT STRING (SIZE (6)),
longitude-r14BIT STRING (SIZE (34)),
altitudeUncertainty-r14BIT STRING (SIZE (6))OPTIONAL,-- Need ON
altitude-r14BIT STRING (SIZE (30))OPTIONAL,-- Need ON
datum-r14BIT STRING (SIZE (8)),
...
}
