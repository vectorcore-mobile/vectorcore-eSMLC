HighAccuracyEllipsoidPointWithAltitudeAndUncertaintyEllipsoid-r15 ::= SEQUENCE {
degreesLatitude-r15INTEGER(-2147483648..2147483647),
degreesLongitude-r15INTEGER(-2147483648..2147483647),
altitude-r15INTEGER(-64000..1280000),
uncertaintySemiMajor-r15INTEGER (0..255),
uncertaintySemiMinor-r15INTEGER (0..255),
orientationMajorAxis-r15INTEGER (0..179),
horizontalConfidence-r15INTEGER (0..100),
uncertaintyAltitude-r15INTEGER (0..255),
verticalConfidence-r15INTEGER (0..100)
}
