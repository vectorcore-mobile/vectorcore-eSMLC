GNSS-Almanac ::= SEQUENCE {
weekNumberINTEGER (0..255)OPTIONAL,-- Need ON
toaINTEGER (0..255)OPTIONAL,-- Need ON
iodaINTEGER (0..3)OPTIONAL,-- Need ON
completeAlmanacProvidedBOOLEAN,
gnss-AlmanacListGNSS-AlmanacList,
...,
[[toa-ext-v1240INTEGER (256..1023)OPTIONAL,-- Need ON
ioda-ext-v1240INTEGER (4..15)OPTIONAL-- Need ON
]],
[[
weekNumber-ext-r16INTEGER (256..8191)OPTIONAL,-- Need ON
toa-ext2-r16INTEGER (256..65535)OPTIONAL-- Need ON
]]
}
GNSS-AlmanacList ::= SEQUENCE (SIZE(1..64)) OF GNSS-AlmanacElement
GNSS-AlmanacElement ::= CHOICE {
keplerianAlmanacSetAlmanacKeplerianSet,-- Model-1
keplerianNAV-AlmanacAlmanacNAV-KeplerianSet,-- Model-2
keplerianReducedAlmanacAlmanacReducedKeplerianSet,-- Model-3
keplerianMidiAlmanacAlmanacMidiAlmanacSet,-- Model-4
keplerianGLONASSAlmanacGLONASS-AlmanacSet,-- Model-5
ecef-SBAS-AlmanacAlmanacECEF-SBAS-AlmanacSet,-- Model-6
...,
keplerianBDS-Almanac-r12AlmanacBDS-AlmanacSet-r12,-- Model-7
keplerianNavIC-Almanac-r16AlmanacNavIC-AlmanacSet-r16-- Model-8
}
