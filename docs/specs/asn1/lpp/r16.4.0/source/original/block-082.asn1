OTDOA-SignalMeasurementInformation ::= SEQUENCE {
systemFrameNumberBIT STRING (SIZE (10)),
physCellIdRefINTEGER (0..503),
cellGlobalIdRefECGIOPTIONAL,
earfcnRefARFCN-ValueEUTRAOPTIONAL,-- Cond NotSameAsRef0
referenceQualityOTDOA-MeasQualityOPTIONAL,
neighbourMeasurementListNeighbourMeasurementList,
...,
[[ earfcnRef-v9a0ARFCN-ValueEUTRA-v9a0OPTIONAL-- Cond NotSameAsRef1
]],
[[ tpIdRef-r14INTEGER (0..4095)OPTIONAL,-- Cond ProvidedByServer0
prsIdRef-r14INTEGER (0..4095)OPTIONAL,-- Cond ProvidedByServer1
additionalPathsRef-r14
AdditionalPathList-r14OPTIONAL,
nprsIdRef-r14INTEGER (0..4095)OPTIONAL,-- Cond ProvidedByServer2
carrierFreqOffsetNB-Ref-r14
CarrierFreqOffsetNB-r14OPTIONAL,-- Cond NB-IoT
hyperSFN-r14BIT STRING (SIZE (10))OPTIONAL-- Cond H-SFN
]],
[[
motionTimeSource-r15MotionTimeSource-r15OPTIONAL
]]
}
NeighbourMeasurementList ::= SEQUENCE (SIZE(1..24)) OF NeighbourMeasurementElement
NeighbourMeasurementElement ::= SEQUENCE {
physCellIdNeighbourINTEGER (0..503),
cellGlobalIdNeighbourECGIOPTIONAL,
earfcnNeighbourARFCN-ValueEUTRAOPTIONAL,-- Cond NotSameAsRef2
rstdINTEGER (0..12711),
rstd-QualityOTDOA-MeasQuality,
...,
[[ earfcnNeighbour-v9a0ARFCN-ValueEUTRA-v9a0OPTIONAL-- Cond NotSameAsRef3
]],
[[ tpIdNeighbour-r14INTEGER (0..4095)OPTIONAL,-- Cond ProvidedByServer0
prsIdNeighbour-r14INTEGER (0..4095)OPTIONAL,-- Cond ProvidedByServer1
delta-rstd-r14INTEGER (0..5)OPTIONAL,
additionalPathsNeighbour-r14
AdditionalPathList-r14OPTIONAL,
nprsIdNeighbour-r14INTEGER (0..4095)OPTIONAL,-- Cond ProvidedByServer2
carrierFreqOffsetNB-Neighbour-r14
CarrierFreqOffsetNB-r14OPTIONAL-- Cond NB-IoT
]],
[[
delta-SFN-r15INTEGER (-8192..8191)OPTIONAL
]]
}
AdditionalPathList-r14 ::= SEQUENCE (SIZE(1..maxPaths-r14)) OF AdditionalPath-r14
maxPaths-r14INTEGER ::= 2
MotionTimeSource-r15 ::= SEQUENCE {
timeSource-r15ENUMERATED {servingCell, referenceCell, gnss, mixed,
other, none, ...}
}
