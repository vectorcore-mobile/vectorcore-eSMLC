GNSS-AcquisitionAssistance ::= SEQUENCE {
gnss-SignalIDGNSS-SignalID,
gnss-AcquisitionAssistListGNSS-AcquisitionAssistList,
...,
confidence-r10INTEGER (0..100)OPTIONAL-- Need ON
}
GNSS-AcquisitionAssistList ::= SEQUENCE (SIZE(1..64)) OF GNSS-AcquisitionAssistElement
GNSS-AcquisitionAssistElement ::= SEQUENCE {
svIDSV-ID,
doppler0INTEGER (-2048..2047),
doppler1INTEGER (0..63),
dopplerUncertaintyINTEGER (0..4),
codePhaseINTEGER (0..1022),
intCodePhaseINTEGER (0..127),
codePhaseSearchWindowINTEGER (0..31),
azimuthINTEGER (0..511),
elevationINTEGER (0..127),
...,
codePhase1023BOOLEANOPTIONAL,-- Need OP
dopplerUncertaintyExt-r10ENUMERATED {d60,
d80,
d100,
d120,
noInformation, ... }OPTIONAL-- Need ON
}
