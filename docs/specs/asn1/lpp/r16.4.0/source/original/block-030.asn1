HighAccuracyEllipsoidPointWithUncertaintyEllipse-r15 ::= SEQUENCE {
degreesLatitude-r15INTEGER(-2147483648..2147483647),
degreesLongitude-r15INTEGER(-2147483648..2147483647),
uncertaintySemiMajor-r15INTEGER (0..255),
uncertaintySemiMinor-r15INTEGER (0..255),
orientationMajorAxis-r15INTEGER (0..179),
confidence-r15INTEGER (0..100)
}
