UTC-ModelSet2 ::= SEQUENCE {
utcA0INTEGER (-32768..32767),
utcA1INTEGER (-4096..4095),
utcA2INTEGER (-64..63),
utcDeltaTlsINTEGER (-128..127),
utcTotINTEGER (0..65535),
utcWNotINTEGER (0..8191),
utcWNlsfINTEGER (0..255),
utcDNBIT STRING (SIZE(4)),
utcDeltaTlsfINTEGER (-128..127),
...,
[[
utcWNlsf-ext-r16INTEGER (256..8191)OPTIONAL-- Need ON
]]
}
