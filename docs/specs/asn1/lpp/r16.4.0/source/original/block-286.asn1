Sensor-ProvideCapabilities-r13 ::= SEQUENCE {
sensor-Modes-r13BIT STRING {standalone(0),
ue-assisted(1),
ue-based(2)} (SIZE (1..8)),
...,
[[sensor-AssistanceDataSupportList-r14Sensor-AssistanceDataSupportList-r14OPTIONAL,
periodicalReportingSupported-r14PositioningModesOPTIONAL,
idleStateForMeasurements-r14ENUMERATED { required }OPTIONAL
]],
[[sensor-MotionInformationSup-r15ENUMERATED { true }OPTIONAL
]],
[[adjustmentSupported-r16ENUMERATED{ true }OPTIONAL
]]
}
Sensor-AssistanceDataSupportList-r14 ::= SEQUENCE {
...,
[[validityPeriodSupported-v1520ENUMERATED { true }OPTIONAL,
validityAreaSupported-v1520ENUMERATED { true }OPTIONAL
]]
}
