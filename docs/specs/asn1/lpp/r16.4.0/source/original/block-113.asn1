StandardClockModelList ::= SEQUENCE (SIZE(1..2)) OF StandardClockModelElement
StandardClockModelElement ::= SEQUENCE {
stanClockTocINTEGER (0..16383),
stanClockAF2INTEGER (-32..31),
stanClockAF1INTEGER (-1048576..1048575),
stanClockAF0INTEGER (-1073741824..1073741823),
stanClockTgdINTEGER (-512..511)OPTIONAL,-- Need ON
sisaINTEGER (0..255),
stanModelIDINTEGER (0..1)OPTIONAL,-- Need ON
...
}
