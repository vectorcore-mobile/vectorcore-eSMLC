BT-ProvideCapabilities-r13 ::= SEQUENCE {
bt-Modes-r13BIT STRING {standalone(0),
ue-assisted(1)}(SIZE (1..8)),
bt-MeasSupported-r13BIT STRING {rssi-r13(0)}(SIZE (1..8)),
...,
[[
idleStateForMeasurements-r14
ENUMERATED {required}OPTIONAL,
periodicalReportingSupported-r14
PositioningModesOPTIONAL
]]
}
