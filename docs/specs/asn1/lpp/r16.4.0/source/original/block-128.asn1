NavModel-NavIC-KeplerianSet-r16 ::= SEQUENCE {
navic-Toe-r16INTEGER (0..65536),
navic-URAI-r16INTEGER (0..15),
navic-W-r16INTEGER (-2147483648..2147483647),
navic-DeltaN-r16INTEGER (-2097152..2097151),
navic-M0-r16INTEGER (-2147483648..2147483647),
navic-OmegaDot-r16INTEGER (-2147483648..2147483647),
navic-E-r16INTEGER (0..4294967295),
navic-IDot-r16INTEGER (-8192..8191),
navic-APowerHalf-r16 INTEGER (0.. 4294967295),
navic-I0-r16INTEGER (-2147483648..2147483647),
navic-Omega0-r16INTEGER (-2147483648..2147483647),
navic-Crs-r16INTEGER (-32768..32767),
navic-Cis-r16INTEGER (-32768..32767),
navic-Cus-r16INTEGER (-32768..32767),
navic-Crc-r16INTEGER (-32768..32767),
navic-Cic-r16INTEGER (-32768..32767),
navic-Cuc-r16INTEGER (-32768..32767),
...
}
