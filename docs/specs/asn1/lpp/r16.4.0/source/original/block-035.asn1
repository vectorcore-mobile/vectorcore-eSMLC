HorizontalWithVerticalVelocityAndUncertainty ::= SEQUENCE {
bearingINTEGER(0..359),
horizontalSpeedINTEGER(0..2047),
verticalDirectionENUMERATED{upward, downward},
verticalSpeedINTEGER(0..255),
horizontalUncertaintySpeedINTEGER(0..255),
verticalUncertaintySpeedINTEGER(0..255)
}
