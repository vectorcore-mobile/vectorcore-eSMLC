OTDOA-NeighbourCellInfoList ::= SEQUENCE (SIZE (1..maxFreqLayers)) OF OTDOA-NeighbourFreqInfo
OTDOA-NeighbourFreqInfo ::= SEQUENCE (SIZE (1..24)) OF OTDOA-NeighbourCellInfoElement
OTDOA-NeighbourCellInfoElement ::= SEQUENCE {
physCellIdINTEGER (0..503),
cellGlobalIdECGIOPTIONAL,-- Need ON
earfcnARFCN-ValueEUTRAOPTIONAL,-- Cond NotSameAsRef0
cpLengthENUMERATED {normal, extended, ...}
OPTIONAL,-- Cond NotSameAsRef1
prsInfoPRS-InfoOPTIONAL,-- Cond NotSameAsRef2
antennaPortConfigENUMERATED {ports-1-or-2, ports-4, ...}
OPTIONAL, -- Cond NotsameAsRef3
slotNumberOffsetINTEGER (0..19)OPTIONAL,-- Cond NotSameAsRef4
prs-SubframeOffsetINTEGER (0..1279)OPTIONAL,-- Cond InterFreq
expectedRSTDINTEGER (0..16383),
expectedRSTD-UncertaintyINTEGER (0..1023),
...,
[[ earfcn-v9a0ARFCN-ValueEUTRA-v9a0OPTIONAL-- Cond NotSameAsRef5
]],
[[tpId-r14INTEGER (0..4095)OPTIONAL,-- Need ON
prs-only-tp-r14ENUMERATED { true }OPTIONAL,-- Cond TBS
cpLengthCRS-r14ENUMERATED { normal, extended, ... }
OPTIONAL,-- Cond CRS
sameMBSFNconfigNeighbour-r14BOOLEANOPTIONAL,-- Need ON
dlBandwidth-r14ENUMERATED {n6, n15, n25, n50, n75, n100}
OPTIONAL,-- Cond NotSameAsRef6
addPRSconfigNeighbour-r14SEQUENCE (SIZE (1..maxAddPRSconfig-r14)) OF
Add-PRSconfigNeighbourElement-r14
OPTIONAL-- Need ON
]],
[[
tdd-config-v1520TDD-Config-v1520OPTIONAL-- Need ON
]]
}
Add-PRSconfigNeighbourElement-r14 ::= SEQUENCE {
add-prsInfo-r14PRS-InfoOPTIONAL,-- Cond NotSameAsRef7
...
}
maxFreqLayersINTEGER ::= 3
