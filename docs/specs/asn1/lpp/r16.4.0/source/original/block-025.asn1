EllipsoidPointWithAltitude ::= SEQUENCE {
latitudeSignENUMERATED {north, south},
degreesLatitudeINTEGER (0..8388607),-- 23 bit field
degreesLongitudeINTEGER (-8388608..8388607),-- 24 bit field
altitudeDirectionENUMERATED {height, depth},
altitudeINTEGER (0..32767)-- 15 bit field
}
