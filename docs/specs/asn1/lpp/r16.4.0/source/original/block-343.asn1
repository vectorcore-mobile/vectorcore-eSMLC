NR-DL-AoD-MeasurementCapability-r16 ::= SEQUENCE {
maxDL-PRS-RSRP-MeasurementFR1-r16INTEGER (1..8),
maxDL-PRS-RSRP-MeasurementFR2-r16INTEGER (1..8),
dl-AoD-MeasCapabilityBandList-r16SEQUENCE (SIZE (1..nrMaxBands-r16)) OF
DL-AoD-MeasCapabilityPerBand-r16,
...
}
DL-AoD-MeasCapabilityPerBand-r16 ::= SEQUENCE {
freqBandIndicatorNR-r16FreqBandIndicatorNR-r16,
simul-NR-DL-AoD-DL-TDOA-r16ENUMERATED { supported}OPTIONAL,
simul-NR-DL-AoD-Multi-RTT-r16ENUMERATED { supported}OPTIONAL,
...
}
