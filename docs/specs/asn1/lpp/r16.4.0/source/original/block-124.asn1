NavModel-GLONASS-ECEF ::= SEQUENCE {
gloEnINTEGER (0..31),
gloP1BIT STRING (SIZE(2)),
gloP2BOOLEAN,
gloMINTEGER (0..3),
gloXINTEGER (-67108864..67108863),
gloXdotINTEGER (-8388608..8388607),
gloXdotdotINTEGER (-16..15),
gloYINTEGER (-67108864..67108863),
gloYdotINTEGER (-8388608..8388607),
gloYdotdotINTEGER (-16..15),
gloZINTEGER (-67108864..67108863),
gloZdotINTEGER (-8388608..8388607),
gloZdotdotINTEGER (-16..15),
...
}
