GNSS-DataBitAssistanceReq ::=SEQUENCE {
gnss-TOD-ReqINTEGER (0..3599),
gnss-TOD-FracReqINTEGER (0..999)OPTIONAL,
dataBitIntervalINTEGER (0..15),
gnss-SignalTypeGNSS-SignalIDs,
gnss-DataBitsReqGNSS-DataBitsReqSatListOPTIONAL,
...
}
GNSS-DataBitsReqSatList ::= SEQUENCE (SIZE(1..64)) OF GNSS-DataBitsReqSatElement
GNSS-DataBitsReqSatElement ::= SEQUENCE {
svIDSV-ID,
...
}
