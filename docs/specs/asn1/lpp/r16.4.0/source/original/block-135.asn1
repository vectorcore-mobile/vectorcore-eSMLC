AlmanacReducedKeplerianSet ::= SEQUENCE {
svIDSV-ID,
redAlmDeltaAINTEGER (-128..127),
redAlmOmega0INTEGER (-64..63),
redAlmPhi0INTEGER (-64..63),
redAlmL1HealthBOOLEAN,
redAlmL2HealthBOOLEAN,
redAlmL5HealthBOOLEAN,
...
}
