GNSS-EarthOrientationParameters ::= SEQUENCE {
teopINTEGER (0..65535),
pmXINTEGER (-1048576..1048575),
pmXdotINTEGER (-16384..16383),
pmYINTEGER (-1048576..1048575),
pmYdotINTEGER (-16384..16383),
deltaUT1INTEGER (-1073741824..1073741823),
deltaUT1dotINTEGER (-262144..262143),
...
}
