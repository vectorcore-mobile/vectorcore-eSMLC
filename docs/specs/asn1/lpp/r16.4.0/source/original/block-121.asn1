NavModelKeplerianSet ::= SEQUENCE {
keplerToeINTEGER (0 .. 16383),
keplerWINTEGER (-2147483648..2147483647),
keplerDeltaNINTEGER (-32768..32767),
keplerM0INTEGER (-2147483648..2147483647),
keplerOmegaDotINTEGER (-8388608.. 8388607),
keplerEINTEGER (0..4294967295),
keplerIDotINTEGER (-8192..8191),
keplerAPowerHalf INTEGER (0.. 4294967295),
keplerI0INTEGER (-2147483648..2147483647),
keplerOmega0INTEGER (-2147483648..2147483647),
keplerCrsINTEGER (-32768..32767),
keplerCisINTEGER (-32768..32767),
keplerCusINTEGER (-32768..32767),
keplerCrcINTEGER (-32768..32767),
keplerCicINTEGER (-32768..32767),
keplerCucINTEGER (-32768..32767),
...
}
