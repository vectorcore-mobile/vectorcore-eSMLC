WLAN-DataSet-r14 ::= SEQUENCE {
wlan-AP-List-r14SEQUENCE (SIZE (1..maxWLAN-AP-r14)) OF WLAN-AP-Data-r14,
supportedChannels-11a-r14SupportedChannels-11a-r14OPTIONAL,-- Need ON
supportedChannels-11bg-r14SupportedChannels-11bg-r14OPTIONAL,-- Need ON
...
}
SupportedChannels-11a-r14 ::= SEQUENCE {
ch34-r14BOOLEAN,
ch36-r14BOOLEAN,
ch38-r14BOOLEAN,
ch40-r14BOOLEAN,
ch42-r14BOOLEAN,
ch44-r14BOOLEAN,
ch46-r14BOOLEAN,
ch48-r14BOOLEAN,
ch52-r14BOOLEAN,
ch56-r14BOOLEAN,
ch60-r14BOOLEAN,
ch64-r14BOOLEAN,
ch149-r14BOOLEAN,
ch153-r14BOOLEAN,
ch157-r14BOOLEAN,
ch161-r14BOOLEAN
}
SupportedChannels-11bg-r14 ::= SEQUENCE {
ch1-r14BOOLEAN,
ch2-r14BOOLEAN,
ch3-r14BOOLEAN,
ch4-r14BOOLEAN,
ch5-r14BOOLEAN,
ch6-r14BOOLEAN,
ch7-r14BOOLEAN,
ch8-r14BOOLEAN,
ch9-r14BOOLEAN,
ch10-r14BOOLEAN,
ch11-r14BOOLEAN,
ch12-r14BOOLEAN,
ch13-r14BOOLEAN,
ch14-r14BOOLEAN
}
