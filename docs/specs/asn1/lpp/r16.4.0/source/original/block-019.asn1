CellGlobalIdEUTRA-AndUTRA ::= SEQUENCE {
plmn-IdentitySEQUENCE {
mccSEQUENCE (SIZE (3))OF INTEGER (0..9),
mncSEQUENCE (SIZE (2..3))OF INTEGER (0..9)
},
cellIdentityCHOICE {
eutraBIT STRING (SIZE (28)),
utraBIT STRING (SIZE (32))
},
...
}
