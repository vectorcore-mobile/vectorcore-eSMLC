AlmanacGLONASS-AlmanacSet ::= SEQUENCE {
gloAlm-NAINTEGER (1..1461),
gloAlmnAINTEGER (1..24),
gloAlmHAINTEGER (0..31),
gloAlmLambdaAINTEGER (-1048576..1048575),
gloAlmtlambdaAINTEGER (0..2097151),
gloAlmDeltaIaINTEGER (-131072..131071),
gloAlmDeltaTAINTEGER (-2097152..2097151),
gloAlmDeltaTdotAINTEGER (-64..63),
gloAlmEpsilonAINTEGER (0..32767),
gloAlmOmegaAINTEGER (-32768..32767),
gloAlmTauAINTEGER (-512..511),
gloAlmCAINTEGER (0..1),
gloAlmMABIT STRING (SIZE(2))OPTIONAL,-- Need ON
...
}
