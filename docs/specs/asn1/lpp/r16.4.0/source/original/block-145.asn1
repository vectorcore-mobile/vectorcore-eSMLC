UTC-ModelSet4 ::= SEQUENCE {
utcA1wntINTEGER (-8388608..8388607),
utcA0wntINTEGER (-2147483648..2147483647),
utcTotINTEGER (0..255),
utcWNtINTEGER (0..255),
utcDeltaTlsINTEGER (-128..127),
utcWNlsfINTEGER (0..255),
utcDNINTEGER (-128..127),
utcDeltaTlsfINTEGER (-128..127),
utcStandardIDINTEGER (0..7),
...
}
