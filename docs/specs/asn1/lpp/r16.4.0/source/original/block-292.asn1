Sensor-AssistanceDataList-r14::= SEQUENCE {
refPressure-r14INTEGER (-20000..10000),
refPosition-r14EllipsoidPointWithAltitudeAndUncertaintyEllipsoidOPTIONAL,-- Need ON
refTemperature-r14INTEGER (-64..63)OPTIONAL,-- Need ON
...,
[[
period-v1520SEQUENCE {
pressureValidityPeriod-v1520PressureValidityPeriod-v1520,
referencePressureRate-v1520INTEGER(-128..127)OPTIONAL,-- Need ON
...
}OPTIONAL,-- Need ON
area-v1520SEQUENCE {
pressureValidityArea-v1520PressureValidityArea-v1520,
gN-pressure-v1520INTEGER (-1024..1023)OPTIONAL,-- Need ON
gE-pressure-v1520INTEGER (-1024..1023)OPTIONAL,-- Need ON
...
}OPTIONAL-- Need ON
]]
}
PressureValidityArea-v1520 ::= SEQUENCE {
centerPoint-v1520Ellipsoid-Point,
validityAreaWidth-v1520INTEGER (1..128),
validityAreaHeight-v1520INTEGER (1..128),
...
}
PressureValidityPeriod-v1520 ::= SEQUENCE {
beginTime-v1520GNSS-SystemTime,
beginTimeAlt-v1520INTEGER (0..2881)OPTIONAL,-- Need ON
duration-v1520INTEGER (1..2881),
...
}
