GNSS-RTK-Observations-r15 ::= SEQUENCE {
epochTime-r15GNSS-SystemTime,
gnss-ObservationList-r15GNSS-ObservationList-r15,
...
}
GNSS-ObservationList-r15 ::= SEQUENCE (SIZE(1..64)) OF GNSS-RTK-SatelliteDataElement-r15
GNSS-RTK-SatelliteDataElement-r15 ::= SEQUENCE{
svID-r15SV-ID,
integer-ms-r15INTEGER (0..254)OPTIONAL,-- Need ON
rough-range-r15INTEGER (0..1023),
rough-phase-range-rate-r15INTEGER (-8192..8191)OPTIONAL,-- Need ON
gnss-rtk-SatelliteSignalDataList-r15GNSS-RTK-SatelliteSignalDataList-r15,
...
}
GNSS-RTK-SatelliteSignalDataList-r15 ::= SEQUENCE (SIZE(1..24)) OF
GNSS-RTK-SatelliteSignalDataElement-r15
GNSS-RTK-SatelliteSignalDataElement-r15 ::= SEQUENCE {
gnss-SignalID-r15GNSS-SignalID,
fine-PseudoRange-r15INTEGER (-524288..524287),
fine-PhaseRange-r15INTEGER (-8388608..8388607),
lockTimeIndicator-r15INTEGER (0..1023),
halfCycleAmbiguityIndicator-r15BIT STRING (SIZE (1)),
carrier-to-noise-ratio-r15INTEGER (0..1023)OPTIONAL,-- Need ON
fine-PhaseRangeRate-r15INTEGER (-16384..16383)OPTIONAL,-- Need ON
...
}
