GNSS-SSR-PhaseBias-r16 ::= SEQUENCE {
epochTime-r16GNSS-SystemTime,
ssrUpdateInterval-r16INTEGER (0..15),
iod-ssr-r16INTEGER (0..15),
ssr-PhaseBiasSatList-r16SSR-PhaseBiasSatList-r16,
...
}
SSR-PhaseBiasSatList-r16 ::= SEQUENCE (SIZE(1..64)) OF SSR-PhaseBiasSatElement-r16
SSR-PhaseBiasSatElement-r16 ::= SEQUENCE {
svID-r16SV-ID,
ssr-PhaseBiasSignalList-r16SSR-PhaseBiasSignalList-r16,
...
}
SSR-PhaseBiasSignalList-r16 ::= SEQUENCE (SIZE(1..16)) OF SSR-PhaseBiasSignalElement-r16
SSR-PhaseBiasSignalElement-r16 ::= SEQUENCE {
signal-and-tracking-mode-ID-r16GNSS-SignalID,
phaseBias-r16INTEGER (-16384..16383),
phaseDiscontinuityIndicator-r16INTEGER (0..3),
phaseBiasIntegerIndicator-r16INTEGER (0..3)OPTIONAL,-- Need OP
...
}
