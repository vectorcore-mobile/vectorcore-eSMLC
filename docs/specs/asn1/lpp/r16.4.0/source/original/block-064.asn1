NR-SelectedDL-PRS-IndexList-r16 ::=SEQUENCE (SIZE (1..nrMaxFreqLayers-r16)) OF
NR-SelectedDL-PRS-PerFreq-r16
NR-SelectedDL-PRS-PerFreq-r16 ::= SEQUENCE {
nr-SelectedDL-PRS-FrequencyLayerIndex-r16INTEGER (0..nrMaxFreqLayers-1-r16),
nr-SelectedDL-PRS-IndexListPerFreq-r16 SEQUENCE (SIZE (1..nrMaxTRPsPerFreq-r16)) OF
NR-SelectedDL-PRS-IndexPerTRP-r16
OPTIONAL,--Need ON
...
}
NR-SelectedDL-PRS-IndexPerTRP-r16 ::= SEQUENCE {
nr-SelectedTRP-Index-r16INTEGER (0..nrMaxTRPsPerFreq-1-r16),
dl-SelectedPRS-ResourceSetIndexList-r16SEQUENCE (SIZE (1..nrMaxSetsPerTrp-r16)) OF
DL-SelectedPRS-ResourceSetIndex-r16
OPTIONAL,--Need ON
...
}
DL-SelectedPRS-ResourceSetIndex-r16 ::= SEQUENCE {
nr-DL-SelectedPRS-ResourceSetIndex-r16INTEGER (0..nrMaxSetsPerTrp-1-r16),
dl-SelectedPRS-ResourceIndexList-r16SEQUENCE (SIZE (1..nrMaxResourcesPerSet-r16)) OF
DL-SelectedPRS-ResourceIndex-r16
OPTIONAL--Need ON
}
DL-SelectedPRS-ResourceIndex-r16 ::= SEQUENCE {
nr-DL-SelectedPRS-ResourceIdIndex-r16INTEGER (0..nrMaxNumDL-PRS-ResourcesPerSet-1-r16),
...
}
