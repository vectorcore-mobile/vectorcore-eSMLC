NR-Multi-RTT-RequestLocationInformation-r16 ::= SEQUENCE {
nr-UE-RxTxTimeDiffMeasurementInfoRequest-r16
ENUMERATED { true }OPTIONAL, -- Need ON
nr-RequestedMeasurements-r16BIT STRING { prsrsrpReq(0)} (SIZE(1..8)),
nr-AssistanceAvailability-r16BOOLEAN,
nr-Multi-RTT-ReportConfig-r16NR-Multi-RTT-ReportConfig-r16,
additionalPaths-r16ENUMERATED { requested }OPTIONAL, -- Need ON
...
}
NR-Multi-RTT-ReportConfig-r16 ::= SEQUENCE {
maxDL-PRS-RxTxTimeDiffMeasPerTRP-r16 INTEGER (1..4)OPTIONAL, -- Need ON
timingReportingGranularityFactor-r16 INTEGER (0..5)OPTIONAL-- Need ON
}
