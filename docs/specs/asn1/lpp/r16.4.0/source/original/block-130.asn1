GNSS-DataBitAssistance ::= SEQUENCE {
gnss-TODINTEGER (0..3599),
gnss-TODfracINTEGER (0..999)OPTIONAL,-- Need ON
gnss-DataBitsSatListGNSS-DataBitsSatList,
...
}
GNSS-DataBitsSatList ::= SEQUENCE (SIZE(1..64))OF GNSS-DataBitsSatElement
GNSS-DataBitsSatElement ::= SEQUENCE {
svIDSV-ID,
gnss-DataBitsSgnListGNSS-DataBitsSgnList,
...
}
GNSS-DataBitsSgnList ::= SEQUENCE (SIZE(1..8)) OF GNSS-DataBitsSgnElement
GNSS-DataBitsSgnElement ::= SEQUENCE {
gnss-SignalTypeGNSS-SignalID,
gnss-DataBitsBIT STRING (SIZE (1..1024)),
...
}
