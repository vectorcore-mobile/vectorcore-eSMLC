GNSS-RTK-Residuals-r15 ::= SEQUENCE {
epochTime-r15GNSS-SystemTime,
referenceStationID-r15GNSS-ReferenceStationID-r15,
n-Refs-r15INTEGER (0..127),
l1-r15GNSS-FrequencyID-r15OPTIONAL,-- Need OP
l2-r15GNSS-FrequencyID-r15OPTIONAL,-- Need OP
rtk-residuals-list-r15RTK-Residuals-List-r15,
...
}
RTK-Residuals-List-r15 ::= SEQUENCE (SIZE(1..64)) OF RTK-Residuals-Element-r15
RTK-Residuals-Element-r15 ::= SEQUENCE {
svID-r15SV-ID,
s-oc-r15INTEGER (0..255),
s-od-r15INTEGER (0..511),
s-oh-r15INTEGER (0..63),
s-lc-r15INTEGER (0..1023),
s-ld-r15INTEGER (0..1023),
...
}
