Polygon ::= SEQUENCE (SIZE (3..15)) OF PolygonPoints
PolygonPoints ::= SEQUENCE {
latitudeSignENUMERATED {north, south},
degreesLatitudeINTEGER (0..8388607),-- 23 bit field
degreesLongitudeINTEGER (-8388608..8388607)-- 24 bit field
}
