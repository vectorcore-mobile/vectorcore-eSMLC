KlobucharModelParameter ::= SEQUENCE {
dataIDBIT STRING (SIZE (2)),
alfa0INTEGER (-128..127),
alfa1INTEGER (-128..127),
alfa2INTEGER (-128..127),
alfa3INTEGER (-128..127),
beta0INTEGER (-128..127),
beta1INTEGER (-128..127),
beta2INTEGER (-128..127),
beta3INTEGER (-128..127),
...
}
