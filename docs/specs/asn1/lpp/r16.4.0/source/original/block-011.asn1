Abort ::= SEQUENCE {
criticalExtensionsCHOICE {
c1CHOICE {
abort-r9Abort-r9-IEs,
spare3 NULL, spare2 NULL, spare1 NULL
},
criticalExtensionsFutureSEQUENCE {}
}
}
Abort-r9-IEs ::= SEQUENCE {
commonIEsAbortCommonIEsAbortOPTIONAL,-- Need ON
...,
epdu-AbortEPDU-SequenceOPTIONAL-- Need ON
}
