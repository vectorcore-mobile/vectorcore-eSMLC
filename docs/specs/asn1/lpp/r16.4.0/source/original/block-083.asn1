OTDOA-SignalMeasurementInformation-NB-r14 ::= SEQUENCE {
systemFrameNumber-r14BIT STRING (SIZE (10)),
physCellIdRef-r14INTEGER (0..503),
cellGlobalIdRef-r14ECGIOPTIONAL,
earfcnRef-r14ARFCN-ValueEUTRA-r14OPTIONAL,-- Cond NotSameAsRef0
referenceQuality-r14OTDOA-MeasQualityOPTIONAL,
neighbourMeasurementList-r14NeighbourMeasurementList-NB-r14,
tpIdRef-r14INTEGER (0..4095)OPTIONAL,-- Cond ProvidedByServer0
prsIdRef-r14INTEGER (0..4095)OPTIONAL,-- Cond ProvidedByServer1
additionalPathsRef-r14AdditionalPathList-r14OPTIONAL,
nprsIdRef-r14INTEGER (0..4095)OPTIONAL,-- Cond ProvidedByServer2
carrierFreqOffsetNB-Ref-r14CarrierFreqOffsetNB-r14OPTIONAL,-- Cond NB-IoT
hyperSFN-r14BIT STRING (SIZE (10))OPTIONAL,-- Cond H-SFN
...
}
NeighbourMeasurementList-NB-r14 ::= SEQUENCE (SIZE(1..24)) OF NeighbourMeasurementElement-NB-r14
NeighbourMeasurementElement-NB-r14 ::= SEQUENCE {
physCellIdNeighbour-r14INTEGER (0..503),
cellGlobalIdNeighbour-r14ECGIOPTIONAL,
earfcnNeighbour-r14ARFCN-ValueEUTRA-r14OPTIONAL,-- Cond NotSameAsRef2
rstd-r14INTEGER (0..12711),
rstd-Quality-r14OTDOA-MeasQuality,
tpIdNeighbour-r14INTEGER (0..4095)OPTIONAL,-- Cond ProvidedByServer0
prsIdNeighbour-r14INTEGER (0..4095)OPTIONAL,-- Cond ProvidedByServer1
delta-rstd-r14INTEGER (0..5)OPTIONAL,
additionalPathsNeighbour-r14
AdditionalPathList-r14OPTIONAL,
nprsIdNeighbour-r14INTEGER (0..4095)OPTIONAL,-- Cond ProvidedByServer2
carrierFreqOffsetNB-Neighbour-r14
CarrierFreqOffsetNB-r14OPTIONAL,-- Cond NB-IoT
...
}
