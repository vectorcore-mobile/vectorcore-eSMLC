OTDOA-ReferenceCellInfoNB-r14 ::= SEQUENCE {
physCellIdNB-r14INTEGER (0..503)OPTIONAL,-- Cond NoPRS-AD1
cellGlobalIdNB-r14ECGIOPTIONAL,-- Cond NoPRS-AD2
carrierFreqRef-r14CarrierFreq-NB-r14OPTIONAL,-- Cond NotSameAsServ1
earfcn-r14ARFCN-ValueEUTRA-r14OPTIONAL,-- Cond Inband
eutra-NumCRS-Ports-r14ENUMERATED {ports1-or-2, ports4}
OPTIONAL,-- Cond NoPRS-AD3
otdoa-SIB1-NB-repetitions-r14ENUMERATED { r4, r8, r16 }OPTIONAL,-- Cond NotSameAsServ2
nprsInfo-r14PRS-Info-NB-r14OPTIONAL,-- Cond NPRS-Type1
...,
[[
nprsInfo-Type2-v1470PRS-Info-NB-r14OPTIONAL-- Cond NPRS-Type2
]],
[[tdd-config-r15TDD-Config-v1520OPTIONAL-- Need ON
]]
}
