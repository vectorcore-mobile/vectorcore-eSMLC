GNSS-RealTimeIntegrity ::= SEQUENCE {
gnss-BadSignalListGNSS-BadSignalList,
...
}
GNSS-BadSignalList ::= SEQUENCE (SIZE(1..64)) OF BadSignalElement
BadSignalElement ::= SEQUENCE {
badSVIDSV-ID,
badSignalIDGNSS-SignalIDsOPTIONAL,-- Need OP
...
}
