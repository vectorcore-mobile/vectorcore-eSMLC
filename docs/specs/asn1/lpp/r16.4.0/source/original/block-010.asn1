ProvideLocationInformation ::= SEQUENCE {
criticalExtensionsCHOICE {
c1CHOICE {
provideLocationInformation-r9ProvideLocationInformation-r9-IEs,
spare3 NULL, spare2 NULL, spare1 NULL
},
criticalExtensionsFutureSEQUENCE {}
}
}
ProvideLocationInformation-r9-IEs ::= SEQUENCE {
commonIEsProvideLocationInformation
CommonIEsProvideLocationInformationOPTIONAL,
a-gnss-ProvideLocationInformationA-GNSS-ProvideLocationInformationOPTIONAL,
otdoa-ProvideLocationInformationOTDOA-ProvideLocationInformationOPTIONAL,
ecid-ProvideLocationInformationECID-ProvideLocationInformationOPTIONAL,
epdu-ProvideLocationInformationEPDU-SequenceOPTIONAL,
...,
[[
sensor-ProvideLocationInformation-r13
Sensor-ProvideLocationInformation-r13
OPTIONAL,
tbs-ProvideLocationInformation-r13TBS-ProvideLocationInformation-r13OPTIONAL,
wlan-ProvideLocationInformation-r13WLAN-ProvideLocationInformation-r13OPTIONAL,
bt-ProvideLocationInformation-r13BT-ProvideLocationInformation-r13OPTIONAL
]],
[[nr-ECID-ProvideLocationInformation-r16
NR-ECID-ProvideLocationInformation-r16OPTIONAL,
nr-Multi-RTT-ProvideLocationInformation-r16
NR-Multi-RTT-ProvideLocationInformation-r16 OPTIONAL,
nr-DL-AoD-ProvideLocationInformation-r16
NR-DL-AoD-ProvideLocationInformation-r16OPTIONAL,
nr-DL-TDOA-ProvideLocationInformation-r16
NR-DL-TDOA-ProvideLocationInformation-r16OPTIONAL
]]
}
