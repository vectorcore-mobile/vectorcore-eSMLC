A-GNSS-ProvideLocationInformation ::= SEQUENCE {
gnss-SignalMeasurementInformationGNSS-SignalMeasurementInformationOPTIONAL,
gnss-LocationInformationGNSS-LocationInformationOPTIONAL,
gnss-ErrorA-GNSS-ErrorOPTIONAL,
...
}
