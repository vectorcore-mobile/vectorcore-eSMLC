PRS-Info-NB-r14 ::= SEQUENCE (SIZE (1..maxCarrier-r14)) OF NPRS-Info-r14
NPRS-Info-r14 ::= SEQUENCE {
operationModeInfoNPRS-r14ENUMERATED { inband, standalone },
nprs-carrier-r14CarrierFreq-NB-r14OPTIONAL,-- Cond Standalone/Guardband
nprsSequenceInfo-r14INTEGER (0..174)OPTIONAL,-- Cond Inband
nprsID-r14INTEGER (0..4095)OPTIONAL,-- Cond NPRS-ID
partA-r14SEQUENCE {
nprsBitmap-r14CHOICE {
subframePattern10-r14BIT STRING (SIZE (10)),
subframePattern40-r14 BIT STRING (SIZE (40))
},
nprs-MutingInfoA-r14CHOICE {
po2-r14BIT STRING (SIZE(2)),
po4-r14BIT STRING (SIZE(4)),
po8-r14BIT STRING (SIZE(8)),
po16-r14BIT STRING (SIZE(16)),
...
}OPTIONAL,-- Cond MutingA
...
}OPTIONAL,-- Cond PartA
partB-r14SEQUENCE {
nprs-Period-r14ENUMERATED { ms160, ms320, ms640, ms1280, ... , ms2560-v1510},
nprs-startSF-r14ENUMERATED { zero, one-eighth, two-eighths, three-eighths,
four-eighths, five-eighths, six-eighths,
seven-eighths, ...},
nprs-NumSF-r14ENUMERATED { sf10, sf20, sf40, sf80, sf160, sf320,
sf640, sf1280, ... , sf2560-v1510},
nprs-MutingInfoB-r14CHOICE {
po2-r14BIT STRING (SIZE(2)),
po4-r14BIT STRING (SIZE(4)),
po8-r14BIT STRING (SIZE(8)),
po16-r14BIT STRING (SIZE(16)),
...
}OPTIONAL,-- Cond MutingB
...,
[[sib1-SF-TDD-r15ENUMERATED {sf0, sf4, sf0and5}OPTIONAL-- Cond SIB1-TDD
]]
}OPTIONAL,-- Cond PartB
...,
[[
partA-TDD-r15SEQUENCE {
nprsBitmap-r15CHOICE {
subframePattern10-TDD-r15BIT STRING (SIZE (8)),
subframePattern40-TDD-r15 BIT STRING (SIZE (32)),
...
},
nprs-MutingInfoA-r15CHOICE {
po2-r15BIT STRING (SIZE(2)),
po4-r15BIT STRING (SIZE(4)),
po8-r15BIT STRING (SIZE(8)),
po16-r15BIT STRING (SIZE(16)),
...
}OPTIONAL,-- Cond MutingA
...
}OPTIONAL-- Cond PartA-TDD
]]
}
maxCarrier-r14INTEGER ::= 5
