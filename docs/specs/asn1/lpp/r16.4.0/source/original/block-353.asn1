NR-Multi-RTT-ProvideCapabilities-r16 ::= SEQUENCE {
nr-Multi-RTT-PRS-Capability-r16NR-DL-PRS-ResourcesCapability-r16,
nr-Multi-RTT-MeasurementCapability-r16NR-Multi-RTT-MeasurementCapability-r16,
nr-DL-PRS-QCL-ProcessingCapability-r16NR-DL-PRS-QCL-ProcessingCapability-r16,
nr-DL-PRS-ProcessingCapability-r16NR-DL-PRS-ProcessingCapability-r16,
nr-UL-SRS-Capability-r16NR-UL-SRS-Capability-r16,
additionalPathsReport-r16ENUMERATED { supported }OPTIONAL,
periodicalReporting-r16ENUMERATED { supported }OPTIONAL,
...
}
