GNSS-RTK-MAC-CorrectionDifferences-r15 ::= SEQUENCE {
networkID-r15GNSS-NetworkID-r15,
subNetworkID-r15GNSS-SubNetworkID-r15OPTIONAL,-- Need ON
master-ReferenceStationID-r15GNSS-ReferenceStationID-r15,
l1-r15GNSS-FrequencyID-r15OPTIONAL,-- Need OP
l2-r15GNSS-FrequencyID-r15OPTIONAL,-- Need OP
rtkCorrectionDifferencesList-r15RTK-CorrectionDifferencesList-r15,
...
}
RTK-CorrectionDifferencesList-r15 ::= SEQUENCE (SIZE (1..32)) OF
RTK-CorrectionDifferencesElement-r15
RTK-CorrectionDifferencesElement-r15 ::= SEQUENCE {
epochTime-r15GNSS-SystemTime,
auxiliary-referenceStationID-r15GNSS-ReferenceStationID-r15,
geometric-ionospheric-corrections-differences-r15
Geometric-Ionospheric-Corrections-Differences-r15,
...
}
Geometric-Ionospheric-Corrections-Differences-r15 ::= SEQUENCE (SIZE(1..64)) OF
Geometric-Ionospheric-Corrections-Differences-Element-r15
Geometric-Ionospheric-Corrections-Differences-Element-r15 ::= SEQUENCE {
svID-r15SV-ID,
ambiguityStatusFlag-r15INTEGER (0..3),
non-synch-count-r15INTEGER (0..7),
geometricCarrierPhaseCorrectionDifference-r15INTEGER (-65536..65535),
iod-r15BIT STRING (SIZE(11)),
ionosphericCarrierPhaseCorrectionDifference-r15INTEGER (-65536..65535),
...
}
