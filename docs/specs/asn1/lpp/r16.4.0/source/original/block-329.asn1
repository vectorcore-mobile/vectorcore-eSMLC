NR-DL-TDOA-RequestLocationInformation-r16 ::= SEQUENCE {
nr-DL-PRS-RstdMeasurementInfoRequest-r16ENUMERATED { true }OPTIONAL,-- Need ON
nr-RequestedMeasurements-r16BIT STRING { prsrsrpReq (0) } (SIZE(1..8)),
nr-AssistanceAvailability-r16BOOLEAN,
nr-DL-TDOA-ReportConfig-r16NR-DL-TDOA-ReportConfig-r16OPTIONAL, -- Need ON
additionalPaths-r16ENUMERATED { requested }OPTIONAL, -- Need ON
...
}
NR-DL-TDOA-ReportConfig-r16 ::= SEQUENCE {
maxDL-PRS-RSTD-MeasurementsPerTRPPair-r16INTEGER (1..4)OPTIONAL, -- Need ON
timingReportingGranularityFactor-r16 INTEGER (0..5)OPTIONAL, -- Need ON
...
}
