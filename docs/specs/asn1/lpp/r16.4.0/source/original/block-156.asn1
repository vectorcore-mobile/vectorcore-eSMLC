GNSS-SSR-ClockCorrections-r15 ::= SEQUENCE {
epochTime-r15GNSS-SystemTime,
ssrUpdateInterval-r15INTEGER (0..15),
iod-ssr-r15INTEGER (0..15),
ssr-ClockCorrectionList-r15SSR-ClockCorrectionList-r15,
...
}
SSR-ClockCorrectionList-r15 ::= SEQUENCE (SIZE(1..64)) OF SSR-ClockCorrectionSatelliteElement-r15
SSR-ClockCorrectionSatelliteElement-r15 ::= SEQUENCE {
svID-r15SV-ID,
delta-Clock-C0-r15INTEGER (-2097152..2097151),
delta-Clock-C1-r15INTEGER (-1048576..1048575)OPTIONAL,
delta-Clock-C2-r15INTEGER (-67108864..67108863)OPTIONAL,
...
}
