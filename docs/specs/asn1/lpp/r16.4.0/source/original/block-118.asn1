BDS-ClockModel-r12 ::= SEQUENCE {
bdsAODC-r12INTEGER (0..31),
bdsToc-r12INTEGER (0..131071),
bdsA0-r12INTEGER (-8388608..8388607),
bdsA1-r12INTEGER (-2097152..2097151),
bdsA2-r12INTEGER (-1024..1023),
bdsTgd1-r12INTEGER (-512..511),
...
}
