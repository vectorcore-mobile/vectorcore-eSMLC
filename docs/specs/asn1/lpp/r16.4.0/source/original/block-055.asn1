NR-DL-PRS-BeamInfo-r16 ::= SEQUENCE (SIZE (1..nrMaxFreqLayers-r16)) OF
NR-DL-PRS-BeamInfoPerFreqLayer-r16
NR-DL-PRS-BeamInfoPerFreqLayer-r16 ::= SEQUENCE (SIZE (1..nrMaxTRPsPerFreq-r16)) OF
NR-DL-PRS-BeamInfoPerTRP-r16
NR-DL-PRS-BeamInfoPerTRP-r16 ::= SEQUENCE {
dl-PRS-ID-r16INTEGER (0..255),
nr-PhysCellID-r16NR-PhysCellID-r16OPTIONAL,-- Need ON
nr-CellGlobalID-r16NCGI-r15OPTIONAL,-- Need ON
nr-ARFCN-r16ARFCN-ValueNR-r15OPTIONAL,-- Need ON
associated-DL-PRS-ID-r16INTEGER (0..255)OPTIONAL,
lcs-GCS-TranslationParameter-r16LCS-GCS-TranslationParameter-r16
OPTIONAL,-- Need OP
dl-PRS-BeamInfoSet-r16DL-PRS-BeamInfoSet-r16OPTIONAL,
...
}
DL-PRS-BeamInfoSet-r16 ::= SEQUENCE (SIZE(1..nrMaxSetsPerTrp-r16)) OF
DL-PRS-BeamInfoResourceSet-r16
DL-PRS-BeamInfoResourceSet-r16 ::= SEQUENCE (SIZE(1..nrMaxResourcesPerSet-r16)) OF
DL-PRS-BeamInfoElement-r16
DL-PRS-BeamInfoElement-r16 ::= SEQUENCE {
dl-PRS-Azimuth-r16INTEGER (0..359),
dl-PRS-Azimuth-fine-r16INTEGER (0..9)OPTIONAL,-- Need ON
dl-PRS-Elevation-r16INTEGER (0..180)OPTIONAL,-- Need ON
dl-PRS-Elevation-fine-r16INTEGER (0..9)OPTIONAL,-- Need ON
...
}
LCS-GCS-TranslationParameter-r16 ::= SEQUENCE {
alpha-r16INTEGER (0..359),
alpha-fine-r16INTEGER (0..9)OPTIONAL,-- Cond AzElFine
beta-r16INTEGER (0..359),
beta-fine-r16INTEGER (0..9)OPTIONAL,-- Cond AzElFine
gamma-r16INTEGER (0..359),
gamma-fine-r16INTEGER (0..9) OPTIONAL,-- Cond AzElFine
...
}
