NR-UL-SRS-Capability-r16 ::= SEQUENCE {
srs-CapabilityBandList-r16SEQUENCE (SIZE (1..nrMaxBands-r16)) OF
SRS-CapabilityPerBand-r16,
srs-PosResourceConfigCA-BandList-r16SEQUENCE (SIZE (1..nrMaxConfiguredBands-r16)) OF
SRS-PosResourcesPerBand-r16OPTIONAL,
maxNumberSRS-PosPathLossEstimateAllServingCells-r16
ENUMERATED {n1, n4, n8, n16}OPTIONAL,
maxNumberSRS-PosSpatialRelationsAllServingCells-r16
ENUMERATED {n0, n1, n2, n4, n8, n16}OPTIONAL,
...
}
SRS-CapabilityPerBand-r16 ::= SEQUENCE {
freqBandIndicatorNR-r16FreqBandIndicatorNR-r16,
olpc-SRS-Pos-r16OLPC-SRS-Pos-r16OPTIONAL,
spatialRelationsSRS-Pos-r16SpatialRelationsSRS-Pos-r16OPTIONAL,
...
}
OLPC-SRS-Pos-r16 ::= SEQUENCE {
olpc-SRS-PosBasedOnPRS-Serving-r16ENUMERATED {supported}OPTIONAL,
olpc-SRS-PosBasedOnSSB-Neigh-r16 ENUMERATED {supported}OPTIONAL,
olpc-SRS-PosBasedOnPRS-Neigh-r16ENUMERATED {supported}OPTIONAL,
maxNumberPathLossEstimatePerServing-r16ENUMERATED {n1, n4, n8, n16}OPTIONAL,
...
}
SpatialRelationsSRS-Pos-r16 ::=SEQUENCE {
spatialRelation-SRS-PosBasedOnSSB-Serving-r16ENUMERATED {supported}OPTIONAL,
spatialRelation-SRS-PosBasedOnCSI-RS-Serving-r16ENUMERATED {supported}OPTIONAL,
spatialRelation-SRS-PosBasedOnPRS-Serving-r16ENUMERATED {supported}OPTIONAL,
spatialRelation-SRS-PosBasedOnSRS-r16ENUMERATED {supported}OPTIONAL,
spatialRelation-SRS-PosBasedOnSSB-Neigh-r16ENUMERATED {supported}OPTIONAL,
spatialRelation-SRS-PosBasedOnPRS-Neigh-r16ENUMERATED {supported}OPTIONAL,
...
}
SRS-PosResourcesPerBand-r16 ::= SEQUENCE {
freqBandIndicatorNR-r16FreqBandIndicatorNR-r16,
maxNumberSRS-PosResourceSetsPerBWP-r16ENUMERATED {n1, n2, n4, n8, n12, n16},
maxNumberSRS-PosResourcesPerBWP-r16ENUMERATED {n1, n2, n4, n8, n16, n32, n64},
maxNumberPeriodicSRS-PosResourcesPerBWP-r16ENUMERATED {n1, n2, n4, n8, n16, n32, n64},
maxNumberAP-SRS-PosResourcesPerBWP-r16ENUMERATED {n1, n2, n4, n8, n16, n32, n64}
OPTIONAL,
maxNumberSP-SRS-PosResourcesPerBWP-r16ENUMERATED {n1, n2, n4, n8, n16, n32, n64}
OPTIONAL,
...
}
