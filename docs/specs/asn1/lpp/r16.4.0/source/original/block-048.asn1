CommonIEsRequestLocationInformation ::= SEQUENCE {
locationInformationTypeLocationInformationType,
triggeredReportingTriggeredReportingCriteriaOPTIONAL,-- Cond ECID
periodicalReportingPeriodicalReportingCriteria OPTIONAL,-- Need ON
additionalInformationAdditionalInformationOPTIONAL,-- Need ON
qosQoSOPTIONAL,-- Need ON
environmentEnvironmentOPTIONAL,-- Need ON
locationCoordinateTypesLocationCoordinateTypesOPTIONAL,-- Need ON
velocityTypesVelocityTypesOPTIONAL,-- Need ON
...,
[[
messageSizeLimitNB-r14MessageSizeLimitNB-r14OPTIONAL-- Need ON
]],
[[
segmentationInfo-r14SegmentationInfo-r14OPTIONAL-- Need ON
]]
}
LocationInformationType ::= ENUMERATED {
locationEstimateRequired,
locationMeasurementsRequired,
locationEstimatePreferred,
locationMeasurementsPreferred,
...
}
PeriodicalReportingCriteria ::=SEQUENCE {
reportingAmountENUMERATED {
ra1, ra2, ra4, ra8, ra16, ra32,
ra64, ra-Infinity
} DEFAULT ra-Infinity,
reportingIntervalENUMERATED {
noPeriodicalReporting, ri0-25,
ri0-5, ri1, ri2, ri4, ri8, ri16, ri32, ri64
}
}
TriggeredReportingCriteria ::=SEQUENCE {
cellChangeBOOLEAN,
reportingDurationReportingDuration,
...
}
ReportingDuration ::=INTEGER (0..255)
AdditionalInformation ::= ENUMERATED {
onlyReturnInformationRequested,
mayReturnAditionalInformation,
...
}
QoS ::= SEQUENCE {
horizontalAccuracyHorizontalAccuracyOPTIONAL,-- Need ON
verticalCoordinateRequestBOOLEAN,
verticalAccuracyVerticalAccuracyOPTIONAL,-- Need ON
responseTimeResponseTimeOPTIONAL,-- Need ON
velocityRequestBOOLEAN,
...,
[[responseTimeNB-r14ResponseTimeNB-r14OPTIONAL-- Need ON
]],
[[horizontalAccuracyExt-r15HorizontalAccuracyExt-r15OPTIONAL,-- Need ON
verticalAccuracyExt-r15VerticalAccuracyExt-r15OPTIONAL-- Need ON
]]
}
HorizontalAccuracy ::= SEQUENCE {
accuracyINTEGER(0..127),
confidenceINTEGER(0..100),
...
}
VerticalAccuracy ::= SEQUENCE {
accuracyINTEGER(0..127),
confidenceINTEGER(0..100),
...
}
HorizontalAccuracyExt-r15 ::= SEQUENCE {
accuracyExt-r15INTEGER(0..255),
confidence-r15INTEGER(0..100),
...
}
VerticalAccuracyExt-r15 ::= SEQUENCE {
accuracyExt-r15INTEGER(0..255),
confidence-r15INTEGER(0..100),
...
}
ResponseTime ::= SEQUENCE {
timeINTEGER (1..128),
...,
[[responseTimeEarlyFix-r12INTEGER (1..128)OPTIONAL-- Need ON
]],
[[unit-r15ENUMERATED { ten-seconds, ... }OPTIONAL-- Need ON
]]
}
ResponseTimeNB-r14 ::= SEQUENCE {
timeNB-r14INTEGER (1..512),
responseTimeEarlyFixNB-r14INTEGER (1..512)OPTIONAL,-- Need ON
...,
[[unitNB-r15ENUMERATED { ten-seconds, ... }OPTIONAL-- Need ON
]]
}
Environment ::= ENUMERATED {
badArea,
notBadArea,
mixedArea,
...
}
MessageSizeLimitNB-r14 ::= SEQUENCE {
measurementLimit-r14INTEGER (1..512)OPTIONAL,-- Need ON
...
}
