NR-ECID-TargetDeviceErrorCauses-r16 ::= SEQUENCE {
cause-r16ENUMERATED {undefined,
requestedMeasurementNotAvailable,
notAllrequestedMeasurementsPossible,
...
},
ss-RSRPMeasurementNotPossible-r16NULLOPTIONAL,
ss-RSRQMeasurementNotPossible-r16NULLOPTIONAL,
csi-RSRPMeasurementNotPossible-r16NULLOPTIONAL,
csi-RSRQMeasurementNotPossible-r16NULLOPTIONAL,
...
}
