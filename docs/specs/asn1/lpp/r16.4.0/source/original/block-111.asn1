GNSS-DifferentialCorrections ::= SEQUENCE {
dgnss-RefTimeINTEGER (0..3599),
dgnss-SgnTypeListDGNSS-SgnTypeList,
...
}
DGNSS-SgnTypeList ::= SEQUENCE (SIZE (1..3)) OF DGNSS-SgnTypeElement
DGNSS-SgnTypeElement ::= SEQUENCE {
gnss-SignalIDGNSS-SignalID,
gnss-StatusHealthINTEGER (0..7),
dgnss-SatListDGNSS-SatList,
...
}
DGNSS-SatList ::= SEQUENCE (SIZE (1..64)) OF DGNSS-CorrectionsElement
DGNSS-CorrectionsElement ::= SEQUENCE {
svIDSV-ID,
iodBIT STRING (SIZE(11)),
udreINTEGER (0..3),
pseudoRangeCorINTEGER (-2047..2047),
rangeRateCorINTEGER (-127..127),
udreGrowthRateINTEGER (0..7)OPTIONAL,-- Need ON
udreValidityTimeINTEGER (0..7)OPTIONAL,-- Need ON
...
}
