OTDOA-ProvideCapabilities ::= SEQUENCE {
otdoa-ModeBIT STRING {ue-assisted(0),
ue-assisted-NB-r14(1),
ue-assisted-NB-TDD-r15(2) } (SIZE (1..8)),
...,
supportedBandListEUTRASEQUENCE (SIZE (1..maxBands)) OF SupportedBandEUTRAOPTIONAL,
supportedBandListEUTRA-v9a0SEQUENCE (SIZE (1..maxBands)) OF SupportedBandEUTRA-v9a0
OPTIONAL,
interFreqRSTDmeasurement-r10ENUMERATED { supported }OPTIONAL,
additionalNeighbourCellInfoList-r10ENUMERATED { supported }OPTIONAL,
prs-id-r14ENUMERATED { supported }OPTIONAL,
tp-separation-via-muting-r14ENUMERATED { supported }OPTIONAL,
additional-prs-config-r14ENUMERATED { supported }OPTIONAL,
prs-based-tbs-r14ENUMERATED { supported }OPTIONAL,
additionalPathsReport-r14ENUMERATED { supported }OPTIONAL,
densePrsConfig-r14ENUMERATED { supported }OPTIONAL,
maxSupportedPrsBandwidth-r14ENUMERATED { n6, n15, n25, n50, n75, n100, ...}OPTIONAL,
prsOccGroup-r14ENUMERATED { supported }OPTIONAL,
prsFrequencyHopping-r14ENUMERATED { supported }OPTIONAL,
maxSupportedPrsConfigs-r14ENUMERATED { c2, c3 }OPTIONAL,
periodicalReporting-r14ENUMERATED { supported }OPTIONAL,
multiPrbNprs-r14ENUMERATED { supported }OPTIONAL,
idleStateForMeasurements-r14ENUMERATED { required }OPTIONAL,
numberOfRXantennas-r14ENUMERATED { rx1, ... }OPTIONAL,
motionMeasurements-r15ENUMERATED { supported }OPTIONAL,
interRAT-RSTDmeasurement-r15ENUMERATED { supported }OPTIONAL
}
maxBands INTEGER ::= 64
SupportedBandEUTRA ::= SEQUENCE {
bandEUTRAINTEGER (1..maxFBI)
}
SupportedBandEUTRA-v9a0 ::=SEQUENCE {
bandEUTRA-v9a0INTEGER (maxFBI-Plus1..maxFBI2)OPTIONAL
}
maxFBIINTEGER::=64-- Maximum value of frequency band indicator
maxFBI-Plus1INTEGER ::= 65-- lowest value extended FBI range
maxFBI2INTEGER ::= 256-- highest value extended FBI range
