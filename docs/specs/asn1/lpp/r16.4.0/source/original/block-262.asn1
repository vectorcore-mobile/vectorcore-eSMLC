ECID-ProvideCapabilities ::= SEQUENCE {
ecid-MeasSupportedBIT STRING {rsrpSup(0),
rsrqSup(1),
ueRxTxSup(2),
nrsrpSup-r14(3),
nrsrqSup-r14(4)} (SIZE(1..8)),
...,
[[ueRxTxSupTDD-r13ENUMERATED { true }OPTIONAL
]],
[[periodicalReporting-r14ENUMERATED { supported }OPTIONAL,
triggeredReporting-r14ENUMERATED { supported }OPTIONAL,
idleStateForMeasurements-r14ENUMERATED { required }OPTIONAL
]]
}
