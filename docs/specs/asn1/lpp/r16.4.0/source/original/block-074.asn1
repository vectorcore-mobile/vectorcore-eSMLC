PRS-Info ::= SEQUENCE {
prs-BandwidthENUMERATED { n6, n15, n25, n50, n75, n100, ... },
prs-ConfigurationIndexINTEGER (0..4095),
numDL-FramesENUMERATED {sf-1, sf-2, sf-4, sf-6, ..., sf-add-v1420},
...,
prs-MutingInfo-r9CHOICE {
po2-r9BIT STRING (SIZE(2)),
po4-r9BIT STRING (SIZE(4)),
po8-r9BIT STRING (SIZE(8)),
po16-r9BIT STRING (SIZE(16)),
...,
po32-v1420BIT STRING (SIZE(32)),
po64-v1420BIT STRING (SIZE(64)),
po128-v1420BIT STRING (SIZE(128)),
po256-v1420BIT STRING (SIZE(256)),
po512-v1420BIT STRING (SIZE(512)),
po1024-v1420BIT STRING (SIZE(1024))
}OPTIONAL,-- Need OP
[[prsID-r14INTEGER (0..4095)OPTIONAL,-- Need ON
add-numDL-Frames-r14INTEGER (1..160)OPTIONAL,-- Cond sf-add
prsOccGroupLen-r14ENUMERATED {g2, g4, g8, g16, g32, g64, g128,... }
OPTIONAL,-- Cond Occ-Grp
prsHoppingInfo-r14CHOICE {
nb2-r14INTEGER (0.. maxAvailNarrowBands-Minus1-r14),
nb4-r14SEQUENCE (SIZE (3))
OF INTEGER (0.. maxAvailNarrowBands-Minus1-r14)
}OPTIONAL-- Cond PRS-FH
]]
}
maxAvailNarrowBands-Minus1-r14INTEGER ::= 15-- Maximum number of narrowbands minus 1
