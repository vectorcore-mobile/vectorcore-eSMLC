GNSS-NavigationModelSupport ::= SEQUENCE {
clockModelBIT STRING {model-1(0),
model-2(1),
model-3(2),
model-4(3),
model-5(4),
model-6(5),
model-7-r16(6),
model-8-r16(7) } (SIZE (1..8))OPTIONAL,
orbitModelBIT STRING {model-1(0),
model-2(1),
model-3(2),
model-4(3),
model-5(4),
model-6(5),
model-7-r16(6),
model-8-r16(7) } (SIZE (1..8))OPTIONAL,
...
}
