TBS-ProvideCapabilities-r13 ::= SEQUENCE {
tbs-Modes-r13BIT STRING {standalone(0),
ue-assisted(1),
ue-based(2)} (SIZE (1..8)),
...,
[[mbs-AssistanceDataSupportList-r14MBS-AssistanceDataSupportList-r14OPTIONAL,
periodicalReportingSupported-r14PositioningModesOPTIONAL,
mbs-ConfigSupport-r14BIT STRING {tb1(0),
tb2(1),
tb3(2),
tb4(3)} (SIZE (1..8))OPTIONAL,
mbs-IdleStateForMeasurements-r14ENUMERATED { required }OPTIONAL
]]
}
