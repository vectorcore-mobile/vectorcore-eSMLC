BDS-DifferentialCorrections-r12 ::= SEQUENCE {
dbds-RefTime-r12INTEGER (0..3599),
bds-SgnTypeList-r12BDS-SgnTypeList-r12,
...
}
BDS-SgnTypeList-r12 ::= SEQUENCE (SIZE (1..3)) OF BDS-SgnTypeElement-r12
BDS-SgnTypeElement-r12 ::= SEQUENCE {
gnss-SignalIDGNSS-SignalIDOPTIONAL,-- Need ON
dbds-CorrectionList-r12DBDS-CorrectionList-r12,
...
}
DBDS-CorrectionList-r12 ::= SEQUENCE (SIZE (1..64)) OF DBDS-CorrectionElement-r12
DBDS-CorrectionElement-r12 ::= SEQUENCE {
svIDSV-ID,
bds-UDREI-r12INTEGER (0..15),
bds-RURAI-r12INTEGER (0..15),
bds-ECC-DeltaT-r12INTEGER (-4096..4095),
...
}
