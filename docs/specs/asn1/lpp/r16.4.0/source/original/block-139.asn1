AlmanacBDS-AlmanacSet-r12 ::= SEQUENCE {
svIDSV-ID,
bdsAlmToa-r12INTEGER (0..255)OPTIONAL,-- Cond NotSameForAllSV
bdsAlmSqrtA-r12INTEGER (0..16777215),
bdsAlmE-r12INTEGER (0..131071),
bdsAlmW-r12INTEGER (-8388608..8388607),
bdsAlmM0-r12INTEGER (-8388608..8388607),
bdsAlmOmega0-r12INTEGER (-8388608..8388607),
bdsAlmOmegaDot-r12INTEGER (-65536..65535),
bdsAlmDeltaI-r12INTEGER (-32768..32767),
bdsAlmA0-r12INTEGER (-1024..1023),
bdsAlmA1-r12INTEGER (-1024..1023),
bdsSvHealth-r12BIT STRING (SIZE(9))OPTIONAL,-- Cond SV-ID
...
}
