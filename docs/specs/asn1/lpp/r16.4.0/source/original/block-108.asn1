GNSS-RTK-AuxiliaryStationData-r15 ::= SEQUENCE {
networkID-r15GNSS-NetworkID-r15,
subNetworkID-r15GNSS-SubNetworkID-r15OPTIONAL,-- Need ON
master-referenceStationID-r15GNSS-ReferenceStationID-r15,
auxiliaryStationList-r15AuxiliaryStationList-r15,
...
}
AuxiliaryStationList-r15 ::= SEQUENCE (SIZE (1..32)) OF AuxiliaryStationElement-r15
AuxiliaryStationElement-r15 ::= SEQUENCE {
aux-referenceStationID-r15GNSS-ReferenceStationID-r15,
aux-master-delta-latitude-r15INTEGER (-524288..524287),
aux-master-delta-longitude-r15INTEGER (-1048576..1048575),
aux-master-delta-height-r15INTEGER (-4194304..4194303),
aux-ARP-unc-r15Aux-ARP-Unc-r15OPTIONAL,-- Need ON
...
}
Aux-ARP-Unc-r15 ::= SEQUENCE {
horizontalUncertainty-r15INTEGER (0..255),
horizontalConfidence-r15INTEGER (0..100),
verticalUncertainty-r15INTEGER (0..255)OPTIONAL,-- Need ON
verticalConfidence-r15INTEGER (0..100)OPTIONAL,-- Need ON
...
}
