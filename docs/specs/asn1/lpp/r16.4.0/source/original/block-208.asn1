GNSS-CommonAssistanceDataSupport ::= SEQUENCE {
gnss-ReferenceTimeSupportGNSS-ReferenceTimeSupport
OPTIONAL, -- Cond RefTimeSup
gnss-ReferenceLocationSupportGNSS-ReferenceLocationSupport
OPTIONAL, -- Cond RefLocSup
gnss-IonosphericModelSupportGNSS-IonosphericModelSupport
OPTIONAL, -- Cond IonoModSup
gnss-EarthOrientationParametersSupportGNSS-EarthOrientationParametersSupport
OPTIONAL, -- Cond EOPSup
...,
[[
gnss-RTK-ReferenceStationInfoSupport-r15
GNSS-RTK-ReferenceStationInfoSupport-r15
OPTIONAL, -- Cond ARPSup
gnss-RTK-AuxiliaryStationDataSupport-r15
GNSS-RTK-AuxiliaryStationDataSupport-r15
OPTIONAL -- Cond AuxARPSup
]]
}
