NavModelCNAV-KeplerianSet ::= SEQUENCE {
cnavTopINTEGER (0..2015),
cnavURAindexINTEGER (-16..15),
cnavDeltaAINTEGER (-33554432..33554431),
cnavAdotINTEGER (-16777216..16777215),
cnavDeltaNoINTEGER (-65536..65535),
cnavDeltaNoDotINTEGER (-4194304..4194303),
cnavMoINTEGER (-4294967296..4294967295),
cnavEINTEGER (0..8589934591),
cnavOmegaINTEGER (-4294967296..4294967295),
cnavOMEGA0INTEGER (-4294967296..4294967295),
cnavDeltaOmegaDotINTEGER (-65536..65535),
cnavIoINTEGER (-4294967296..4294967295),
cnavIoDotINTEGER (-16384..16383),
cnavCisINTEGER (-32768..32767),
cnavCicINTEGER (-32768..32767),
cnavCrsINTEGER (-8388608..8388607),
cnavCrcINTEGER (-8388608..8388607),
cnavCusINTEGER (-1048576..1048575),
cnavCucINTEGER (-1048576..1048575),
...
}
