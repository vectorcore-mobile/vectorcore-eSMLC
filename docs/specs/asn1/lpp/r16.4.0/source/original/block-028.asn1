EPDU-Sequence ::= SEQUENCE (SIZE (1..maxEPDU)) OF EPDU
maxEPDU INTEGER ::= 16
EPDU ::= SEQUENCE {
ePDU-IdentifierEPDU-Identifier,
ePDU-BodyEPDU-Body
}
EPDU-Identifier ::= SEQUENCE {
ePDU-IDEPDU-ID,
ePDU-NameEPDU-NameOPTIONAL,
...
}
EPDU-ID ::= INTEGER (1..256)
EPDU-Name ::= VisibleString (SIZE (1..32))
EPDU-Body ::= OCTET STRING
