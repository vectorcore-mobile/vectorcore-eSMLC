NR-Multi-RTT-ProvideAssistanceData-r16 ::= SEQUENCE {
nr-DL-PRS-AssistanceData-r16NR-DL-PRS-AssistanceData-r16OPTIONAL,-- Need ON
nr-SelectedDL-PRS-IndexList-r16NR-SelectedDL-PRS-IndexList-r16 OPTIONAL,-- Need ON
nr-Multi-RTT-Error-r16NR-Multi-RTT-Error-r16OPTIONAL,-- Need ON
...
}
