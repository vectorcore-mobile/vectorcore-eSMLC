UTC-ModelSet1 ::= SEQUENCE {
gnss-Utc-A1INTEGER (-8388608..8388607),
gnss-Utc-A0INTEGER (-2147483648..2147483647),
gnss-Utc-TotINTEGER (0..255),
gnss-Utc-WNtINTEGER (0..255),
gnss-Utc-DeltaTlsINTEGER (-128..127),
gnss-Utc-WNlsfINTEGER (0..255),
gnss-Utc-DNINTEGER (-128..127),
gnss-Utc-DeltaTlsfINTEGER (-128..127),
...
}
