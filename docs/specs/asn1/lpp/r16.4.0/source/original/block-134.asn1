AlmanacNAV-KeplerianSet ::= SEQUENCE {
svIDSV-ID,
navAlmEINTEGER (0..65535),
navAlmDeltaIINTEGER (-32768..32767),
navAlmOMEGADOTINTEGER (-32768..32767),
navAlmSVHealthINTEGER (0..255),
navAlmSqrtAINTEGER (0..16777215),
navAlmOMEGAoINTEGER (-8388608..8388607),
navAlmOmegaINTEGER (-8388608..8388607),
navAlmMoINTEGER (-8388608..8388607),
navAlmaf0INTEGER (-1024..1023),
navAlmaf1INTEGER (-1024..1023),
...
}
