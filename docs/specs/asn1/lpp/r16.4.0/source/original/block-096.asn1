GNSS-ReferenceTime ::= SEQUENCE {
gnss-SystemTimeGNSS-SystemTime,
referenceTimeUncINTEGER (0..127)OPTIONAL,-- Cond noFTA
gnss-ReferenceTimeForCellsSEQUENCE (SIZE (1..16)) OF
GNSS-ReferenceTimeForOneCellOPTIONAL,-- Need ON
...
}
GNSS-ReferenceTimeForOneCell ::= SEQUENCE {
networkTimeNetworkTime,
referenceTimeUncINTEGER (0..127),
bsAlignENUMERATED {true}OPTIONAL,
...
}
