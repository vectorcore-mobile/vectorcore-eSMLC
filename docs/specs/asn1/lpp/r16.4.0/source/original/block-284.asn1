Sensor-MotionInformation-r15 ::= SEQUENCE {
refTime-r15DisplacementTimeStamp-r15,
displacementInfoList-r15DisplacementInfoList-r15,
...
}
DisplacementInfoList-r15 ::= SEQUENCE (SIZE (1..128)) OF DisplacementInfoListElement-r15
DisplacementInfoListElement-r15 ::= SEQUENCE {
deltaTimeStamp-r15DeltaTime-r15,
displacement-r15Displacement-r15OPTIONAL,
...
}
DisplacementTimeStamp-r15 ::= CHOICE {
utcTime-r15UTC-Time-r15,
gnssTime-r15MeasurementReferenceTime,
systemFrameNumber-r15SFN-r15,
measurementSFN-r15INTEGER(-8192..9214),
...
}
DeltaTime-r15 ::= CHOICE {
deltaTimeSec-r15INTEGER (1..16384),
deltaTimeSFN-r15INTEGER (1..4096),
...
}
SFN-r15 ::= SEQUENCE {
sfn-r15BIT STRING (SIZE (10)),
hyperSFN-r15BIT STRING (SIZE (10))OPTIONAL,
...
}
Displacement-r15 ::= SEQUENCE {
bearing-r15INTEGER (0..3599),
bearingUncConfidence-r15INTEGER (0..100)OPTIONAL,
bearingRef-r15ENUMERATED { geographicNorth, magneticNorth, local },
horizontalDistance-r15INTEGER (0..8191),
horizontalDistanceUnc-r15INTEGER (0..255)OPTIONAL,
horizontalUncConfidence-r15INTEGER (0..100)OPTIONAL,
verticalDirection-r15ENUMERATED{upward, downward}OPTIONAL,
verticalDistance-r15INTEGER(0..8191)OPTIONAL,
verticalDistanceUnc-r15INTEGER (0..255)OPTIONAL,
verticalUncConfidence-r15INTEGER (0..100)OPTIONAL,
...
}
UTC-Time-r15 ::= SEQUENCE {
utcTime-r15UTCTime,
utcTime-ms-r15INTEGER (0..999),
...
}
