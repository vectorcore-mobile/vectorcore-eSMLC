NR-DL-PRS-AssistanceData-r16 ::= SEQUENCE {
nr-DL-PRS-ReferenceInfo-r16 DL-PRS-ID-Info-r16,
nr-DL-PRS-AssistanceDataList-r16SEQUENCE (SIZE (1..nrMaxFreqLayers-r16)) OF
NR-DL-PRS-AssistanceDataPerFreq-r16,
nr-SSB-Config-r16SEQUENCE (SIZE (1..nrMaxTRPs-r16)) OF
NR-SSB-Config-r16OPTIONAL,-- Need ON
...
}
NR-DL-PRS-AssistanceDataPerFreq-r16 ::= SEQUENCE {
nr-DL-PRS-PositioningFrequencyLayer-r16
NR-DL-PRS-PositioningFrequencyLayer-r16,
nr-DL-PRS-AssistanceDataPerFreq-r16 SEQUENCE (SIZE (1..nrMaxTRPsPerFreq-r16)) OF
NR-DL-PRS-AssistanceDataPerTRP-r16,
...
}
NR-DL-PRS-AssistanceDataPerTRP-r16 ::= SEQUENCE {
dl-PRS-ID-r16INTEGER (0..255),
nr-PhysCellID-r16NR-PhysCellID-r16OPTIONAL,-- Need ON
nr-CellGlobalID-r16NCGI-r15OPTIONAL,-- Need ON
nr-ARFCN-r16ARFCN-ValueNR-r15OPTIONAL,-- Need ON
nr-DL-PRS-SFN0-Offset-r16NR-DL-PRS-SFN0-Offset-r16,
nr-DL-PRS-ExpectedRSTD-r16INTEGER (-3841..3841),
nr-DL-PRS-ExpectedRSTD-Uncertainty-r16
INTEGER (0..246),
nr-DL-PRS-Info-r16NR-DL-PRS-Info-r16,
...
}
NR-DL-PRS-PositioningFrequencyLayer-r16 ::= SEQUENCE {
dl-PRS-SubcarrierSpacing-r16ENUMERATED {kHz15, kHz30, kHz60, kHz120, ...},
dl-PRS-ResourceBandwidth-r16INTEGER (1..63),
dl-PRS-StartPRB-r16INTEGER (0..2176),
dl-PRS-PointA-r16ARFCN-ValueNR-r15,
dl-PRS-CombSizeN-r16ENUMERATED {n2, n4, n6, n12, ...},
dl-PRS-CyclicPrefix-r16ENUMERATED {normal, extended, ...},
...
}
NR-DL-PRS-SFN0-Offset-r16 ::= SEQUENCE {
sfn-Offset-r16INTEGER (0..1023),
integerSubframeOffset-r16INTEGER (0..9),
...}
