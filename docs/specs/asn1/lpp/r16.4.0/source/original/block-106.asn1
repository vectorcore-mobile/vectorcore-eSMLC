GNSS-RTK-ReferenceStationInfo-r15 ::= SEQUENCE {
referenceStationID-r15GNSS-ReferenceStationID-r15,
referenceStationIndicator-r15ENUMERATED {physical, non-physical},
antenna-reference-point-ECEF-X-r15INTEGER (-137438953472..137438953471),
antenna-reference-point-ECEF-Y-r15INTEGER (-137438953472..137438953471),
antenna-reference-point-ECEF-Z-r15INTEGER (-137438953472..137438953471),
antennaHeight-r15INTEGER (0..65535)OPTIONAL, -- Need ON
antennaDescription-r15AntennaDescription-r15OPTIONAL, -- Need ON
antenna-reference-point-unc-r15AntennaReferencePointUnc-r15OPTIONAL, -- Need ON
physical-reference-station-info-r15PhysicalReferenceStationInfo-r15OPTIONAL, -- Cond NP
...,
[[
equalIntegerAmbiguityLevel-r16EqualIntegerAmbiguityLevel-r16OPTIONAL -- Need ON
]]
}
AntennaDescription-r15 ::= SEQUENCE {
antennaDescriptor-r15VisibleString (SIZE (1..256)),
antennaSetUpID-r15ENUMERATED { non-zero }OPTIONAL, -- Need OP
...
}
AntennaReferencePointUnc-r15 ::= SEQUENCE {
uncertainty-X-r15INTEGER (0..255),
confidence-X-r15INTEGER (0..100),
uncertainty-Y-r15INTEGER (0..255),
confidence-Y-r15INTEGER (0..100),
uncertainty-Z-r15INTEGER (0..255),
confidence-Z-r15INTEGER (0..100),
...
}
PhysicalReferenceStationInfo-r15 ::= SEQUENCE {
physicalReferenceStationID-r15GNSS-ReferenceStationID-r15,
physical-ARP-ECEF-X-r15INTEGER (-137438953472..137438953471),
physical-ARP-ECEF-Y-r15INTEGER (-137438953472..137438953471),
physical-ARP-ECEF-Z-r15INTEGER (-137438953472..137438953471),
physical-ARP-unc-r15AntennaReferencePointUnc-r15OPTIONAL, -- Need ON
...
}
EqualIntegerAmbiguityLevel-r16 ::= CHOICE {
allReferenceStations-r16NULL,
referenceStationList-r16ReferenceStationList-r16
}
ReferenceStationList-r16 ::= SEQUENCE (SIZE(1..16)) OF GNSS-ReferenceStationID-r15
