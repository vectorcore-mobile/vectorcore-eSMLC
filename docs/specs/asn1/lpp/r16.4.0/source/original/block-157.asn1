GNSS-SSR-CodeBias-r15 ::= SEQUENCE {
epochTime-r15GNSS-SystemTime,
ssrUpdateInterval-r15INTEGER (0..15),
iod-ssr-r15INTEGER (0..15),
ssr-CodeBiasSatList-r15SSR-CodeBiasSatList-r15,
...
}
SSR-CodeBiasSatList-r15 ::= SEQUENCE (SIZE(1..64)) OF SSR-CodeBiasSatElement-r15
SSR-CodeBiasSatElement-r15 ::= SEQUENCE {
svID-r15SV-ID,
ssr-CodeBiasSignalList-r15SSR-CodeBiasSignalList-r15,
...
}
SSR-CodeBiasSignalList-r15 ::= SEQUENCE (SIZE(1..16)) OF SSR-CodeBiasSignalElement-r15
SSR-CodeBiasSignalElement-r15 ::= SEQUENCE {
signal-and-tracking-mode-ID-r15GNSS-SignalID,
codeBias-r15INTEGER (-8192..8191),
...
}
