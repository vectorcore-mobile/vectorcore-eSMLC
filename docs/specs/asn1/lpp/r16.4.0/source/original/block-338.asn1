NR-DL-AoD-ProvideLocationInformation-r16 ::= SEQUENCE {
nr-DL-AoD-SignalMeasurementInformation-r16
NR-DL-AoD-SignalMeasurementInformation-r16
OPTIONAL,
nr-dl-AoD-LocationInformation-r16NR-DL-AoD-LocationInformation-r16
OPTIONAL, -- Cond UEB
nr-DL-AoD-Error-r16NR-DL-AoD-Error-r16OPTIONAL,
...
}
