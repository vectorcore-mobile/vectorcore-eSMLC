NR-DL-TDOA-ProvideCapabilities-r16 ::= SEQUENCE {
nr-DL-TDOA-Mode-r16PositioningModes,
nr-DL-TDOA-PRS-Capability-r16NR-DL-PRS-ResourcesCapability-r16,
nr-DL-TDOA-MeasurementCapability-r16NR-DL-TDOA-MeasurementCapability-r16,
nr-DL-PRS-QCL-ProcessingCapability-r16NR-DL-PRS-QCL-ProcessingCapability-r16,
nr-DL-PRS-ProcessingCapability-r16NR-DL-PRS-ProcessingCapability-r16,
additionalPathsReport-r16ENUMERATED { supported }OPTIONAL,
periodicalReporting-r16PositioningModesOPTIONAL,
...
}
