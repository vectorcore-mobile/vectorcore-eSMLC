WLAN-RequestAssistanceData-r14 ::= SEQUENCE {
requestedAD-r14BIT STRING {ap-identifier(0),
ap-location(1)}(SIZE (1..8)),
visibleAPs-r14SEQUENCE (SIZE (1..maxVisibleAPs-r14)) OF WLAN-AP-Identifier-r13OPTIONAL,
wlan-AP-StoredData-r14SEQUENCE (SIZE (1..maxKnownAPs-r14)) OF WLAN-AP-Identifier-r13OPTIONAL,
...
}
