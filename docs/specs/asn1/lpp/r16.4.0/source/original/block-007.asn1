RequestAssistanceData ::= SEQUENCE {
criticalExtensionsCHOICE {
c1CHOICE {
requestAssistanceData-r9RequestAssistanceData-r9-IEs,
spare3 NULL, spare2 NULL, spare1 NULL
},
criticalExtensionsFutureSEQUENCE {}
}
}
RequestAssistanceData-r9-IEs ::= SEQUENCE {
commonIEsRequestAssistanceDataCommonIEsRequestAssistanceDataOPTIONAL,
a-gnss-RequestAssistanceDataA-GNSS-RequestAssistanceDataOPTIONAL,
otdoa-RequestAssistanceDataOTDOA-RequestAssistanceDataOPTIONAL,
epdu-RequestAssistanceDataEPDU-SequenceOPTIONAL,
...,
[[sensor-RequestAssistanceData-r14
Sensor-RequestAssistanceData-r14OPTIONAL,
tbs-RequestAssistanceData-r14TBS-RequestAssistanceData-r14OPTIONAL,
wlan-RequestAssistanceData-r14WLAN-RequestAssistanceData-r14OPTIONAL
]],
[[nr-Multi-RTT-RequestAssistanceData-r16NR-Multi-RTT-RequestAssistanceData-r16OPTIONAL,
nr-DL-AoD-RequestAssistanceData-r16NR-DL-AoD-RequestAssistanceData-r16OPTIONAL,
nr-DL-TDOA-RequestAssistanceData-r16NR-DL-TDOA-RequestAssistanceData-r16OPTIONAL
]]
}
