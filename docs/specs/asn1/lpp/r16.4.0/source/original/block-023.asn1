Ellipsoid-PointWithUncertaintyCircle ::= SEQUENCE {
latitudeSignENUMERATED {north, south},
degreesLatitudeINTEGER (0..8388607),-- 23 bit field
degreesLongitudeINTEGER (-8388608..8388607),-- 24 bit field
uncertaintyINTEGER (0..127)
}
