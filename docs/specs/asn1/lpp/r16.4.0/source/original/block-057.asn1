NR-DL-PRS-ProcessingCapability-r16 ::= SEQUENCE {
prs-ProcessingCapabilityBandList-r16SEQUENCE (SIZE (1..nrMaxBands-r16)) OF
PRS-ProcessingCapabilityPerBand-r16,
maxSupportedFreqLayers-r16INTEGER (1..4),
simulLTE-NR-PRS-r16ENUMERATED { supported}OPTIONAL,
...
}
PRS-ProcessingCapabilityPerBand-r16 ::= SEQUENCE {
freqBandIndicatorNR-r16FreqBandIndicatorNR-r16,
supportedBandwidthPRS-r16CHOICE {
fr1ENUMERATED {mhz5, mhz10, mhz20, mhz40,
mhz50, mhz80, mhz100},
fr2ENUMERATED {mhz50, mhz100, mhz200, mhz400},
...
},
dl-PRS-BufferType-r16 ENUMERATED {type1, type2, ...},
durationOfPRS-Processing-r16SEQUENCE {
durationOfPRS-ProcessingSymbols-r16ENUMERATED {nDot125, nDot25, nDot5, n1,
n2, n4, n6, n8, n12, n16, n20, n25,
n30, n32, n35, n40, n45, n50},
durationOfPRS-ProcessingSymbolsInEveryTms-r16
ENUMERATED {n8, n16, n20, n30, n40, n80,
n160,n320, n640, n1280},
...
},
maxNumOfDL-PRS-ResProcessedPerSlot-r16SEQUENCE {
scs15-r16ENUMERATED {n1, n2, n4, n8, n16, n24, n32,
n48, n64}OPTIONAL,
scs30-r16ENUMERATED {n1, n2, n4, n8, n16, n24, n32,
n48, n64}OPTIONAL,
scs60-r16ENUMERATED {n1, n2, n4, n8, n16, n24, n32,
n48, n64}OPTIONAL,
scs120-r16ENUMERATED {n1, n2, n4, n8, n16, n24, n32,
n48, n64}OPTIONAL,
...
},
...
}
