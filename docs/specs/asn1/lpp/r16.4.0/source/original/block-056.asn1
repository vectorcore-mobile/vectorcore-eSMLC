NR-DL-PRS-Info-r16 ::= SEQUENCE {
nr-DL-PRS-ResourceSetList-r16SEQUENCE (SIZE (1..nrMaxSetsPerTrp-r16)) OF
NR-DL-PRS-ResourceSet-r16,
...
}
NR-DL-PRS-ResourceSet-r16 ::= SEQUENCE {
nr-DL-PRS-ResourceSetID-r16NR-DL-PRS-ResourceSetID-r16,
dl-PRS-Periodicity-and-ResourceSetSlotOffset-r16
NR-DL-PRS-Periodicity-and-ResourceSetSlotOffset-r16,
dl-PRS-ResourceRepetitionFactor-r16ENUMERATED {n2, n4, n6, n8, n16, n32, ...}
OPTIONAL,-- Need OP
dl-PRS-ResourceTimeGap-r16ENUMERATED {s1, s2, s4, s8, s16, s32, ...}
OPTIONAL, -- Cond Rep
dl-PRS-NumSymbols-r16ENUMERATED {n2, n4, n6, n12, ...},
dl-PRS-MutingOption1-r16DL-PRS-MutingOption1-r16OPTIONAL,-- Need OP
dl-PRS-MutingOption2-r16DL-PRS-MutingOption2-r16OPTIONAL,-- Need OP
dl-PRS-ResourcePower-r16INTEGER (-60..50),
dl-PRS-ResourceList-r16SEQUENCE (SIZE (1..nrMaxResourcesPerSet-r16)) OF
NR-DL-PRS-Resource-r16,
...
}
DL-PRS-MutingOption1-r16 ::= SEQUENCE {
dl-prs-MutingBitRepetitionFactor-r16
ENUMERATED { n1, n2, n4, n8, ... }OPTIONAL,-- Need OP
nr-option1-muting-r16NR-MutingPattern-r16,
...
}
DL-PRS-MutingOption2-r16 ::= SEQUENCE {
nr-option2-muting-r16NR-MutingPattern-r16,
...
}
NR-MutingPattern-r16 ::= CHOICE {
po2-r16BIT STRING (SIZE(2)),
po4-r16BIT STRING (SIZE(4)),
po6-r16BIT STRING (SIZE(6)),
po8-r16BIT STRING (SIZE(8)),
po16-r16BIT STRING (SIZE(16)),
po32-r16BIT STRING (SIZE(32)),
...
}
NR-DL-PRS-Resource-r16 ::= SEQUENCE {
nr-DL-PRS-ResourceID-r16NR-DL-PRS-ResourceID-r16,
dl-PRS-SequenceID-r16INTEGER (0.. 4095),
dl-PRS-CombSizeN-AndReOffset-r16CHOICE {
n2-r16INTEGER (0..1),
n4-r16INTEGER (0..3),
n6-r16INTEGER (0..5),
n12-r16INTEGER (0..11),
...
},
dl-PRS-ResourceSlotOffset-r16INTEGER (0..nrMaxResourceOffsetValue-1-r16),
dl-PRS-ResourceSymbolOffset-r16INTEGER (0..12),
dl-PRS-QCL-Info-r16DL-PRS-QCL-Info-r16OPTIONAL,
...
}
DL-PRS-QCL-Info-r16 ::= CHOICE {
ssb-r16SEQUENCE {
pci-r16NR-PhysCellID-r16,
ssb-Index-r16INTEGER (0..63),
rs-Type-r16ENUMERATED {typeC, typeD, typeC-plus-typeD}
},
dl-PRS-r16SEQUENCE {
qcl-DL-PRS-ResourceID-r16NR-DL-PRS-ResourceID-r16,
qcl-DL-PRS-ResourceSetID-r16NR-DL-PRS-ResourceSetID-r16
}
}
NR-DL-PRS-Periodicity-and-ResourceSetSlotOffset-r16 ::= CHOICE {
scs15-r16CHOICE {
n4-r16INTEGER (0..3),
n5-r16INTEGER (0..4),
n8-r16INTEGER (0..7),
n10-r16INTEGER (0..9),
n16-r16INTEGER (0..15),
n20-r16INTEGER (0..19),
n32-r16INTEGER (0..31),
n40-r16INTEGER (0..39),
n64-r16INTEGER (0..63),
n80-r16INTEGER (0..79),
n160-r16INTEGER (0..159),
n320-r16INTEGER (0..319),
n640-r16INTEGER (0..639),
n1280-r16INTEGER (0..1279),
n2560-r16INTEGER (0..2559),
n5120-r16INTEGER (0..5119),
n10240-r16INTEGER (0..10239),
...
},
scs30-r16CHOICE {
n8-r16INTEGER (0..7),
n10-r16INTEGER (0..9),
n16-r16INTEGER (0..15),
n20-r16INTEGER (0..19),
n32-r16INTEGER (0..31),
n40-r16INTEGER (0..39),
n64-r16INTEGER (0..63),
n80-r16INTEGER (0..79),
n128-r16INTEGER (0..127),
n160-r16INTEGER (0..159),
n320-r16INTEGER (0..319),
n640-r16INTEGER (0..639),
n1280-r16INTEGER (0..1279),
n2560-r16INTEGER (0..2559),
n5120-r16INTEGER (0..5119),
n10240-r16INTEGER (0..10239),
n20480-r16INTEGER (0..20479),
...
},
scs60-r16CHOICE {
n16-r16INTEGER (0..15),
n20-r16INTEGER (0..19),
n32-r16INTEGER (0..31),
n40-r16INTEGER (0..39),
n64-r16INTEGER (0..63),
n80-r16INTEGER (0..79),
n128-r16INTEGER (0..127),
n160-r16INTEGER (0..159),
n256-r16INTEGER (0..255),
n320-r16INTEGER (0..319),
n640-r16INTEGER (0..639),
n1280-r16INTEGER (0..1279),
n2560-r16INTEGER (0..2559),
n5120-r16INTEGER (0..5119),
n10240-r16INTEGER (0..10239),
n20480-r16INTEGER (0..20479),
n40960-r16INTEGER (0..40959),
...
},
scs120-r16CHOICE {
n32-r16INTEGER (0..31),
n40-r16INTEGER (0..39),
n64-r16INTEGER (0..63),
n80-r16INTEGER (0..79),
n128-r16INTEGER (0..127),
n160-r16INTEGER (0..159),
n256-r16INTEGER (0..255),
n320-r16INTEGER (0..319),
n512-r16INTEGER (0..511),
n640-r16INTEGER (0..639),
n1280-r16INTEGER (0..1279),
n2560-r16INTEGER (0..2559),
n5120-r16INTEGER (0..5119),
n10240-r16INTEGER (0..10239),
n20480-r16INTEGER (0..20479),
n40960-r16INTEGER (0..40959),
n81920-r16INTEGER (0..81919),
...
},
...
}
