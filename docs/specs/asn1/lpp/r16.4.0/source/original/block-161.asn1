GNSS-SSR-GriddedCorrection-r16 ::= SEQUENCE {
epochTime-r16GNSS-SystemTime,
ssrUpdateInterval-r16INTEGER (0..15),
iod-ssr-r16INTEGER (0..15),
troposphericDelayQualityIndicator-r16BIT STRING (SIZE(6))OPTIONAL, -- Cond Tropo
correctionPointSetID-r16INTEGER (0..16383),
gridList-r16GridList-r16,
...
}
GridList-r16 ::= SEQUENCE (SIZE(1..64)) OF GridElement-r16
GridElement-r16 ::= SEQUENCE {
tropospericDelayCorrection-r16TropospericDelayCorrection-r16OPTIONAL,
stec-ResidualSatList-r16STEC-ResidualSatList-r16OPTIONAL,
...
}
TropospericDelayCorrection-r16 ::= SEQUENCE {
tropoHydroStaticVerticalDelay-r16INTEGER (-256..255),
tropoWetVerticalDelay-r16INTEGER (-128..127),
...
}
STEC-ResidualSatList-r16 ::= SEQUENCE (SIZE(1..64)) OF STEC-ResidualSatElement-r16
STEC-ResidualSatElement-r16 ::= SEQUENCE {
svID-r16SV-ID,
stecResidualCorrection-r16CHOICE {
b7-r16INTEGER (-64..63),
b16-r16INTEGER (-32768..32767)
},
...
}
