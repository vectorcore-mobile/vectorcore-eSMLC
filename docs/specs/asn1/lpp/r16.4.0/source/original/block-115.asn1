CNAV-ClockModel ::= SEQUENCE {
cnavTocINTEGER (0..2015),
cnavTopINTEGER (0..2015),
cnavURA0INTEGER (-16..15),
cnavURA1INTEGER (0..7),
cnavURA2INTEGER (0..7),
cnavAf2INTEGER (-512..511),
cnavAf1INTEGER (-524288..524287),
cnavAf0INTEGER (-33554432..33554431),
cnavTgdINTEGER (-4096..4095),
cnavISCl1cpINTEGER (-4096..4095)OPTIONAL,-- Need ON
cnavISCl1cdINTEGER (-4096..4095)OPTIONAL,-- Need ON
cnavISCl1caINTEGER (-4096..4095)OPTIONAL,-- Need ON
cnavISCl2cINTEGER (-4096..4095)OPTIONAL,-- Need ON
cnavISCl5i5INTEGER (-4096..4095)OPTIONAL,-- Need ON
cnavISCl5q5INTEGER (-4096..4095)OPTIONAL,-- Need ON
...
}
