UTC-ModelSet3 ::= SEQUENCE {
nAINTEGER (1..1461),
tauCINTEGER (-2147483648..2147483647),
b1INTEGER (-1024..1023)OPTIONAL,-- Cond GLONASS-M
b2INTEGER (-512..511)OPTIONAL,-- Cond GLONASS-M
kpBIT STRING (SIZE(2))OPTIONAL,-- Cond GLONASS-M
...
}
