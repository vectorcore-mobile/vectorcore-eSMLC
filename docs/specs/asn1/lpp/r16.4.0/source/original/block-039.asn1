PeriodicAssistanceDataControlParameters-r15 ::= SEQUENCE {
periodicSessionID-r15PeriodicSessionID-r15,
...,
[[
updateCapabilities-r15UpdateCapabilities-r15OPTIONAL
]]
}
PeriodicSessionID-r15 ::= SEQUENCE {
periodicSessionInitiator-r15ENUMERATED { locationServer, targetDevice, ... },
periodicSessionNumber-r15INTEGER (0..255),
...
}
UpdateCapabilities-r15 ::= BIT STRING {primaryCellID-r15(0)} (SIZE(1..8))
