OTDOA-TargetDeviceErrorCauses ::= SEQUENCE {
causeENUMERATED {undefined,
assistance-data-missing,
unableToMeasureReferenceCell,
unableToMeasureAnyNeighbourCell,
attemptedButUnableToMeasureSomeNeighbourCells,
...
},
...
}
