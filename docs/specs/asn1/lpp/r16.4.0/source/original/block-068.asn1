NR-TRP-LocationInfo-r16 ::= SEQUENCE (SIZE (1..nrMaxFreqLayers-r16)) OF
NR-TRP-LocationInfoPerFreqLayer-r16
NR-TRP-LocationInfoPerFreqLayer-r16 ::= SEQUENCE {
referencePoint-r16ReferencePoint-r16OPTIONAL,-- Cond NotSameAsPrev
trp-LocationInfoList-r16SEQUENCE (SIZE (1..nrMaxTRPsPerFreq-r16)) OF
TRP-LocationInfoElement-r16,
...
}
TRP-LocationInfoElement-r16 ::= SEQUENCE {
dl-PRS-ID-r16INTEGER (0..255),
nr-PhysCellID-r16NR-PhysCellID-r16OPTIONAL,-- Need ON
nr-CellGlobalID-r16NCGI-r15OPTIONAL,-- Need ON
nr-ARFCN-r16ARFCN-ValueNR-r15OPTIONAL,-- Need ON
associated-DL-PRS-ID-r16INTEGER (0..255)OPTIONAL,
trp-Location-r16RelativeLocation-r16OPTIONAL,-- Need OP
trp-DL-PRS-ResourceSets-r16SEQUENCE (SIZE(1..nrMaxSetsPerTrp-r16)) OF
DL-PRS-ResourceSets-TRP-Element-r16OPTIONAL,-- Need OP
...
}
DL-PRS-ResourceSets-TRP-Element-r16 ::= SEQUENCE {
dl-PRS-ResourceSetARP-r16RelativeLocation-r16OPTIONAL,-- Need OP
dl-PRS-Resource-ARP-List-r16SEQUENCE (SIZE(1..nrMaxResourcesPerSet-r16)) OF
DL-PRS-Resource-ARP-Element-r16OPTIONAL,-- Need OP
...
}
DL-PRS-Resource-ARP-Element-r16 ::= SEQUENCE {
dl-PRS-Resource-ARP-location-r16RelativeLocation-r16OPTIONAL,-- Need OP
...
}
