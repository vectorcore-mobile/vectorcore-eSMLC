NR-DL-TDOA-SignalMeasurementInformation-r16 ::= SEQUENCE {
dl-PRS-ReferenceInfo-r16DL-PRS-ID-Info-r16,
nr-DL-TDOA-MeasList-r16NR-DL-TDOA-MeasList-r16,
...
}
NR-DL-TDOA-MeasList-r16 ::= SEQUENCE (SIZE(1..nrMaxTRPs-r16)) OF NR-DL-TDOA-MeasElement-r16
NR-DL-TDOA-MeasElement-r16 ::= SEQUENCE {
dl-PRS-ID-r16INTEGER (0..255),
nr-PhysCellID-r16NR-PhysCellID-r16OPTIONAL,
nr-CellGlobalID-r16NCGI-r15OPTIONAL,
nr-ARFCN-r16ARFCN-ValueNR-r15OPTIONAL,
nr-DL-PRS-ResourceID-r16NR-DL-PRS-ResourceID-r16 OPTIONAL,
nr-DL-PRS-ResourceSetID-r16NR-DL-PRS-ResourceSetID-r16OPTIONAL,
nr-TimeStamp-r16NR-TimeStamp-r16,
nr-RSTD-r16CHOICE {
k0-r16INTEGER (0..1970049),
k1-r16INTEGER (0..985025),
k2-r16INTEGER (0..492513),
k3-r16INTEGER (0..246257),
k4-r16INTEGER (0..123129),
k5-r16INTEGER (0..61565),
...
},
nr-AdditionalPathList-r16NR-AdditionalPathList-r16OPTIONAL,
nr-TimingQuality-r16NR-TimingQuality-r16,
nr-DL-PRS-RSRP-Result-r16INTEGER (0..126)OPTIONAL,
nr-DL-TDOA-AdditionalMeasurements-r16
NR-DL-TDOA-AdditionalMeasurements-r16OPTIONAL,
...
}
NR-DL-TDOA-AdditionalMeasurements-r16 ::= SEQUENCE (SIZE (1..3)) OF
NR-DL-TDOA-AdditionalMeasurementElement-r16
NR-DL-TDOA-AdditionalMeasurementElement-r16 ::= SEQUENCE {
nr-DL-PRS-ResourceID-r16NR-DL-PRS-ResourceID-r16 OPTIONAL,
nr-DL-PRS-ResourceSetID-r16NR-DL-PRS-ResourceSetID-r16 OPTIONAL,
nr-TimeStamp-r16NR-TimeStamp-r16,
nr-RSTD-ResultDiff-r16CHOICE {
k0-r16INTEGER (0..8191),
k1-r16INTEGER (0..4095),
k2-r16INTEGER (0..2047),
k3-r16INTEGER (0..1023),
k4-r16INTEGER (0..511),
k5-r16INTEGER (0..255),
...
},
nr-TimingQuality-r16NR-TimingQuality-r16,
nr-DL-PRS-RSRP-ResultDiff-r16INTEGER (0..61)OPTIONAL,
nr-AdditionalPathList-r16NR-AdditionalPathList-r16OPTIONAL,
...
}
