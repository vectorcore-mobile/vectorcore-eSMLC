NavModel-SBAS-ECEF ::= SEQUENCE {
sbasToINTEGER (0..5399)OPTIONAL,-- Cond ClockModel
sbasAccuracyBIT STRING (SIZE(4)),
sbasXgINTEGER (-536870912..536870911),
sbasYgINTEGER (-536870912..536870911),
sbasZgINTEGER (-16777216..16777215),
sbasXgDotINTEGER (-65536..65535),
sbasYgDotINTEGER (-65536..65535),
sbasZgDotINTEGER (-131072..131071),
sbasXgDotDotINTEGER (-512..511),
sbagYgDotDotINTEGER (-512..511),
sbasZgDotDotINTEGER (-512..511),
...
}
