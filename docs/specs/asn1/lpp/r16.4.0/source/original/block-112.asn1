GNSS-NavigationModel ::= SEQUENCE {
nonBroadcastIndFlagINTEGER (0..1),
gnss-SatelliteListGNSS-NavModelSatelliteList,
...
}
GNSS-NavModelSatelliteList ::= SEQUENCE (SIZE(1..64)) OF GNSS-NavModelSatelliteElement
GNSS-NavModelSatelliteElement ::= SEQUENCE {
svIDSV-ID,
svHealthBIT STRING (SIZE(8)),
iodBIT STRING (SIZE(11)),
gnss-ClockModelGNSS-ClockModel,
gnss-OrbitModelGNSS-OrbitModel,
...,
[[svHealthExt-v1240 BIT STRING (SIZE(4))OPTIONAL-- Need ON
]]
}
GNSS-ClockModel ::= CHOICE {
standardClockModelListStandardClockModelList,-- Model-1
nav-ClockModelNAV-ClockModel,-- Model-2
cnav-ClockModelCNAV-ClockModel,-- Model-3
glonass-ClockModelGLONASS-ClockModel,-- Model-4
sbas-ClockModelSBAS-ClockModel,-- Model-5
...,
bds-ClockModel-r12BDS-ClockModel-r12,-- Model-6
bds-ClockModel2-r16BDS-ClockModel2-r16,-- Model-7
navic-ClockModel-r16NavIC-ClockModel-r16-- Model-8
}
GNSS-OrbitModel ::= CHOICE {
keplerianSetNavModelKeplerianSet,-- Model-1
nav-KeplerianSetNavModelNAV-KeplerianSet,-- Model-2
cnav-KeplerianSetNavModelCNAV-KeplerianSet,-- Model-3
glonass-ECEFNavModel-GLONASS-ECEF,-- Model-4
sbas-ECEFNavModel-SBAS-ECEF,-- Model-5
...,
bds-KeplerianSet-r12NavModel-BDS-KeplerianSet-r12,-- Model-6
bds-KeplerianSet2-r16NavModel-BDS-KeplerianSet2-r16,-- Model-7
navic-KeplerianSet-r16NavModel-NavIC-KeplerianSet-r16-- Model-8
}
