GNSS-LocationServerErrorCauses ::= SEQUENCE {
causeENUMERATED{
undefined,
undeliveredAssistanceDataIsNotSupportedByServer,
undeliveredAssistanceDataIsSupportedButCurrentlyNotAvailableByServer,undeliveredAssistanceDataIsPartlyNotSupportedAndPartlyNotAvailableByServer,
...,
unconfirmedPeriodicAssistanceDataIsNotSupported-v1510,
unconfirmedPeriodicAssistanceDataIsSupportedButCurrentlyNotAvailable-v1510,
unconfirmedPeriodicAssistanceDataIsPartlyNotSupportedAndPartlyNotAvailable-v1510,
undeliveredPeriodicAssistanceDataIsCurrentlyNotAvailable-v1510
},
...
}
