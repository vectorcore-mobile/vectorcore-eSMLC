NR-TimeStamp-r16 ::= SEQUENCE {
dl-PRS-ID-r16INTEGER (0..255),
nr-PhysCellID-r16NR-PhysCellID-r16OPTIONAL,-- Need ON
nr-CellGlobalID-r16NCGI-r15OPTIONAL,-- Need ON
nr-ARFCN-r16ARFCN-ValueNR-r15OPTIONAL,-- Need ON
nr-SFN-r16INTEGER (0..1023),
nr-Slot-r16 CHOICE {
scs15-r16INTEGER (0..9),
scs30-r16INTEGER (0..19),
scs60-r16INTEGER (0..39),
scs120-r16INTEGER (0..79)
},
...
}
