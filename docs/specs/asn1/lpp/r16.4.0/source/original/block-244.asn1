GNSS-TargetDeviceErrorCauses ::= SEQUENCE {
causeENUMERATED {undefined,
thereWereNotEnoughSatellitesReceived,
assistanceDataMissing,
notAllRequestedMeasurementsPossible,
...
},
fineTimeAssistanceMeasurementsNotPossibleNULLOPTIONAL,
adrMeasurementsNotPossibleNULLOPTIONAL,
multiFrequencyMeasurementsNotPossibleNULLOPTIONAL,
...
}
