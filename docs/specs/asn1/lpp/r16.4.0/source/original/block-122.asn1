NavModelNAV-KeplerianSet ::= SEQUENCE {
navURAINTEGER (0..15),
navFitFlagINTEGER (0..1),
navToeINTEGER (0..37799),
navOmegaINTEGER (-2147483648..2147483647),
navDeltaNINTEGER (-32768..32767),
navM0INTEGER (-2147483648..2147483647),
navOmegaADotINTEGER (-8388608..8388607),
navEINTEGER (0..4294967295),
navIDotINTEGER (-8192..8191),
navAPowerHalfINTEGER (0..4294967295),
navI0INTEGER (-2147483648..2147483647),
navOmegaA0INTEGER (-2147483648..2147483647),
navCrsINTEGER (-32768..32767),
navCisINTEGER (-32768..32767),
navCusINTEGER (-32768..32767),
navCrcINTEGER (-32768..32767),
navCicINTEGER (-32768..32767),
navCucINTEGER (-32768..32767),
addNAVparamSEQUENCE {
ephemCodeOnL2INTEGER (0..3),
ephemL2PflagINTEGER (0..1),
ephemSF1RsvdSEQUENCE {
reserved1INTEGER (0..8388607),-- 23-bit field
reserved2INTEGER (0..16777215),-- 24-bit field
reserved3INTEGER (0..16777215),-- 24-bit field
reserved4INTEGER (0..65535)-- 16-bit field
},
ephemAODAINTEGER (0..31)
}OPTIONAL,-- Need ON
...
}
