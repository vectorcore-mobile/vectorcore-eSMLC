LPP-Broadcast-Definitions
DEFINITIONS AUTOMATIC TAGS ::=
BEGIN
IMPORTS
OTDOA-ReferenceCellInfo,
OTDOA-NeighbourCellInfoList,
NR-TRP-LocationInfo-r16,
NR-DL-PRS-BeamInfo-r16,
NR-RTD-Info-r16
FROM LPP-PDU-Definitions;

AssistanceDataSIBelement-r15 ::= SEQUENCE {
valueTag-r15INTEGER (0..63)OPTIONAL,
expirationTime-r15UTCTimeOPTIONAL,
cipheringKeyData-r15CipheringKeyData-r15 OPTIONAL,
segmentationInfo-r15SegmentationInfo-r15OPTIONAL,
assistanceDataElement-r15OCTET STRING,
...
}
CipheringKeyData-r15 ::= SEQUENCE {
cipherSetID-r15 INTEGER (0..65535),
d0-r15 BIT STRING (SIZE (1..128)),
...
}
SegmentationInfo-r15 ::= SEQUENCE {
segmentationOption-r15ENUMERATED {pseudo-seg, octet-string-seg},
assistanceDataSegmentType-r15ENUMERATED {notLastSegment, lastSegment},
assistanceDataSegmentNumber-r15INTEGER (0..63),
...
}

OTDOA-UE-Assisted-r15 ::= SEQUENCE {
otdoa-ReferenceCellInfo-r15OTDOA-ReferenceCellInfo,
otdoa-NeighbourCellInfo-r15OTDOA-NeighbourCellInfoList,
...
}

NR-UEB-TRP-LocationData-r16 ::= SEQUENCE {
nr-trp-LocationInfo-r16 NR-TRP-LocationInfo-r16,
nr-dl-prs-BeamInfo-r16NR-DL-PRS-BeamInfo-r16OPTIONAL,-- Need ON
...
}

NR-UEB-TRP-RTD-Info-r16 ::= SEQUENCE {
nr-rtd-Info-r16NR-RTD-Info-r16,
...
}

END
