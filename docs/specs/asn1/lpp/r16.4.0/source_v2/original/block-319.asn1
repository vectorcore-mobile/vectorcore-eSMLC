NR-ECID-ProvideCapabilities-r16 ::= SEQUENCE {
	nr-ECID-MeasSupported-r16		BIT STRING {	ssrsrpSup		(0),
													ssrsrqSup		(1),
													csirsrpSup		(2),
													csirsrqSup		(3)} (SIZE(1..8)),
	periodicalReporting-r16		ENUMERATED { supported }							OPTIONAL,
	triggeredReporting-r16		ENUMERATED { supported }							OPTIONAL,
	...
}
