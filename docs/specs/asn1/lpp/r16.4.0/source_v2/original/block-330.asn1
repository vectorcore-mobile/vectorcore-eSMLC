NR-DL-TDOA-ProvideCapabilities-r16 ::= SEQUENCE {
	nr-DL-TDOA-Mode-r16						PositioningModes,
	nr-DL-TDOA-PRS-Capability-r16			NR-DL-PRS-ResourcesCapability-r16,
	nr-DL-TDOA-MeasurementCapability-r16	NR-DL-TDOA-MeasurementCapability-r16,
	nr-DL-PRS-QCL-ProcessingCapability-r16	NR-DL-PRS-QCL-ProcessingCapability-r16,
	nr-DL-PRS-ProcessingCapability-r16		NR-DL-PRS-ProcessingCapability-r16,
	additionalPathsReport-r16				ENUMERATED { supported }					OPTIONAL,
	periodicalReporting-r16					PositioningModes							OPTIONAL,
	...
}
