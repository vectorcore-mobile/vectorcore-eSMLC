GNSS-AlmanacSupport ::=	SEQUENCE {
	almanacModel		BIT STRING {	model-1		(0),
										model-2		(1),
										model-3		(2),
										model-4		(3),
										model-5		(4),
										model-6		(5),
										model-7		(6) } (SIZE (1..8))		OPTIONAL,
	...
}
