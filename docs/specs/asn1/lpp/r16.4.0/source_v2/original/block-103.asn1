KlobucharModel2Parameter-r16 ::= SEQUENCE {
	alfa1-r16			INTEGER (0..1023),
	alfa2-r16			INTEGER (-128..127),
	alfa3-r16			INTEGER (0..255),
	alfa4-r16			INTEGER (0..255),
	alfa5-r16			INTEGER (0..255),
	alfa6-r16			INTEGER (-128..127),
	alfa7-r16			INTEGER (-128..127),
	alfa8-r16			INTEGER (-128..127),
	alfa9-r16			INTEGER (-128..127),
	...
}
