NR-DL-TDOA-RequestLocationInformation-r16 ::= SEQUENCE {
	nr-DL-PRS-RstdMeasurementInfoRequest-r16	ENUMERATED { true }				OPTIONAL,-- Need ON
	nr-RequestedMeasurements-r16				BIT STRING { prsrsrpReq (0) } (SIZE(1..8)),
	nr-AssistanceAvailability-r16				BOOLEAN,
	nr-DL-TDOA-ReportConfig-r16					NR-DL-TDOA-ReportConfig-r16		OPTIONAL, -- Need ON
	additionalPaths-r16							ENUMERATED { requested }		OPTIONAL, -- Need ON
	...
}
NR-DL-TDOA-ReportConfig-r16 ::= SEQUENCE {
	maxDL-PRS-RSTD-MeasurementsPerTRPPair-r16	INTEGER (1..4)					OPTIONAL, -- Need ON
	timingReportingGranularityFactor-r16 		INTEGER (0..5)					OPTIONAL, -- Need ON
	...
}
