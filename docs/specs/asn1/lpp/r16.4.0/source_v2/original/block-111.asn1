GNSS-DifferentialCorrections ::= SEQUENCE {
	dgnss-RefTime		INTEGER (0..3599),
	dgnss-SgnTypeList	DGNSS-SgnTypeList,
	...
}
DGNSS-SgnTypeList ::= SEQUENCE (SIZE (1..3)) OF DGNSS-SgnTypeElement
DGNSS-SgnTypeElement ::= SEQUENCE {
	gnss-SignalID		GNSS-SignalID,
	gnss-StatusHealth	INTEGER (0..7),
	dgnss-SatList		DGNSS-SatList,
	...
}
DGNSS-SatList ::= SEQUENCE (SIZE (1..64)) OF DGNSS-CorrectionsElement
DGNSS-CorrectionsElement ::= SEQUENCE {
	svID				SV-ID,
	iod				BIT STRING (SIZE(11)),
	udre				INTEGER (0..3),		
	pseudoRangeCor		INTEGER (-2047..2047),
	rangeRateCor		INTEGER (-127..127),
	udreGrowthRate		INTEGER (0..7)			OPTIONAL,	-- Need ON
	udreValidityTime	INTEGER (0..7)			OPTIONAL,	-- Need ON	
	...
}
