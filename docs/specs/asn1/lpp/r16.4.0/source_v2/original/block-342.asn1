NR-DL-AoD-ProvideCapabilities-r16 ::= SEQUENCE {
	nr-DL-AoD-Mode-r16						PositioningModes,
	nr-DL-AoD-PRS-Capability-r16			NR-DL-PRS-ResourcesCapability-r16,
	nr-DL-AoD-MeasurementCapability-r16		NR-DL-AoD-MeasurementCapability-r16,
	nr-DL-PRS-QCL-ProcessingCapability-r16	NR-DL-PRS-QCL-ProcessingCapability-r16,
	nr-DL-PRS-ProcessingCapability-r16		NR-DL-PRS-ProcessingCapability-r16,
	periodicalReporting-r16					PositioningModes						OPTIONAL,
	...
}
