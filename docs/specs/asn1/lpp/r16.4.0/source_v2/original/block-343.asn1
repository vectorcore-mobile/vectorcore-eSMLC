NR-DL-AoD-MeasurementCapability-r16 ::= SEQUENCE {
	maxDL-PRS-RSRP-MeasurementFR1-r16		INTEGER (1..8),
	maxDL-PRS-RSRP-MeasurementFR2-r16		INTEGER (1..8),
	dl-AoD-MeasCapabilityBandList-r16		SEQUENCE (SIZE (1..nrMaxBands-r16)) OF
													DL-AoD-MeasCapabilityPerBand-r16,
	...
}
DL-AoD-MeasCapabilityPerBand-r16 ::= SEQUENCE {
	freqBandIndicatorNR-r16				FreqBandIndicatorNR-r16,
	simul-NR-DL-AoD-DL-TDOA-r16			ENUMERATED { supported}	OPTIONAL,
	simul-NR-DL-AoD-Multi-RTT-r16		ENUMERATED { supported}	OPTIONAL,
	...
}
