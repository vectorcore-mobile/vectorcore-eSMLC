GNSS-GenericAssistanceDataSupport ::=
								SEQUENCE (SIZE (1..16)) OF GNSS-GenericAssistDataSupportElement
GNSS-GenericAssistDataSupportElement ::= SEQUENCE {
	gnss-ID								GNSS-ID,
	sbas-ID								SBAS-ID						OPTIONAL, -- Cond GNSSIDSBAS
	gnss-TimeModelsSupport				GNSS-TimeModelListSupport
																	OPTIONAL, -- Cond TimeModSup
	gnss-DifferentialCorrectionsSupport	GNSS-DifferentialCorrectionsSupport
																	OPTIONAL, -- Cond DGNSS-Sup
	gnss-NavigationModelSupport			GNSS-NavigationModelSupport
																	OPTIONAL, -- Cond NavModSup
	gnss-RealTimeIntegritySupport		GNSS-RealTimeIntegritySupport
																	OPTIONAL, -- Cond RTISup
	gnss-DataBitAssistanceSupport		GNSS-DataBitAssistanceSupport
																	OPTIONAL, -- Cond DataBitsSup
	gnss-AcquisitionAssistanceSupport	GNSS-AcquisitionAssistanceSupport
																	OPTIONAL, -- Cond AcquAssistSup
	gnss-AlmanacSupport					GNSS-AlmanacSupport
																	OPTIONAL, -- Cond AlmanacSup
	gnss-UTC-ModelSupport				GNSS-UTC-ModelSupport
																	OPTIONAL, -- Cond UTCModSup
	gnss-AuxiliaryInformationSupport	GNSS-AuxiliaryInformationSupport
																	OPTIONAL, -- Cond AuxInfoSup
	...,
		[[
			bds-DifferentialCorrectionsSupport-r12
										BDS-DifferentialCorrectionsSupport-r12
																	OPTIONAL, -- Cond DBDS-Sup
		bds-GridModelSupport-r12		BDS-GridModelSupport-r12
																			OPTIONAL	-- Cond BDS-GridModSup
	]],
	[[
		gnss-RTK-ObservationsSupport-r15
										GNSS-RTK-ObservationsSupport-r15
																	OPTIONAL,	-- Cond RTK-OSR-Sup
		glo-RTK-BiasInformationSupport-r15	
										GLO-RTK-BiasInformationSupport-r15	
																	OPTIONAL,	-- Cond GLO-CPB-Sup
		gnss-RTK-MAC-CorrectionDifferencesSupport-r15
										GNSS-RTK-MAC-CorrectionDifferencesSupport-r15
																	OPTIONAL,	-- Cond MAC-Sup
		gnss-RTK-ResidualsSupport-r15	GNSS-RTK-ResidualsSupport-r15
																	OPTIONAL,	-- Cond Res-Sup
		gnss-RTK-FKP-GradientsSupport-r15
										GNSS-RTK-FKP-GradientsSupport-r15
																	OPTIONAL,	-- Cond FKP-Sup
		gnss-SSR-OrbitCorrectionsSupport-r15
										GNSS-SSR-OrbitCorrectionsSupport-r15
																	OPTIONAL, 	-- Cond OC-Sup
		gnss-SSR-ClockCorrectionsSupport-r15
										GNSS-SSR-ClockCorrectionsSupport-r15
																	OPTIONAL, 	-- Cond CC-Sup
		gnss-SSR-CodeBiasSupport-r15	GNSS-SSR-CodeBiasSupport-r15
																	OPTIONAL 	-- Cond CB-Sup
	]],
		[[
		gnss-SSR-URA-Support-r16		GNSS-SSR-URA-Support-r16	OPTIONAL,	-- Cond URA-Sup
		gnss-SSR-PhaseBiasSupport-r16	GNSS-SSR-PhaseBiasSupport-r16		
																	OPTIONAL,	-- Cond PB-Sup
		gnss-SSR-STEC-CorrectionSupport-r16
										GNSS-SSR-STEC-CorrectionSupport-r16
																	OPTIONAL,	-- Cond STEC-Sup
		gnss-SSR-GriddedCorrectionSupport-r16
										GNSS-SSR-GriddedCorrectionSupport-r16
																	OPTIONAL,	-- Cond Grid-Sup
			navic-DifferentialCorrectionsSupport-r16
										NavIC-DifferentialCorrectionsSupport-r16
																OPTIONAL,	-- Cond DNavIC-Sup
		navic-GridModelSupport-r16		NavIC-GridModelSupport-r16
																		OPTIONAL	-- Cond NavIC-GridModSup
	]]
}
