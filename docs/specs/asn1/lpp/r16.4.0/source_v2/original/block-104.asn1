NeQuickModelParameter ::= SEQUENCE {
	ai0			INTEGER (0..2047),
	ai1			INTEGER (-1024..1023),
	ai2			INTEGER (-8192..8191),
	ionoStormFlag1	INTEGER (0..1)		OPTIONAL,	-- Need OP
	ionoStormFlag2	INTEGER (0..1)		OPTIONAL,	-- Need OP
	ionoStormFlag3	INTEGER (0..1)		OPTIONAL,	-- Need OP
	ionoStormFlag4	INTEGER (0..1)		OPTIONAL,	-- Need OP
	ionoStormFlag5	INTEGER (0..1)		OPTIONAL,	-- Need OP
	...
}
