LPP-Broadcast-Definitions
DEFINITIONS AUTOMATIC TAGS ::=
BEGIN
IMPORTS
	OTDOA-ReferenceCellInfo,
	OTDOA-NeighbourCellInfoList,
	NR-TRP-LocationInfo-r16,
	NR-DL-PRS-BeamInfo-r16,
	NR-RTD-Info-r16	
FROM LPP-PDU-Definitions;
