GNSS-GenericAssistDataReq ::= SEQUENCE (SIZE (1..16)) OF GNSS-GenericAssistDataReqElement
GNSS-GenericAssistDataReqElement ::= SEQUENCE {
	gnss-ID							GNSS-ID,
	sbas-ID							SBAS-ID							OPTIONAL, -- Cond GNSS-ID-SBAS
	gnss-TimeModelsReq				GNSS-TimeModelListReq			OPTIONAL, -- Cond TimeModReq
	gnss-DifferentialCorrectionsReq	GNSS-DifferentialCorrectionsReq	OPTIONAL, -- Cond DGNSS-Req
	gnss-NavigationModelReq			GNSS-NavigationModelReq			OPTIONAL, -- Cond NavModReq
	gnss-RealTimeIntegrityReq		GNSS-RealTimeIntegrityReq		OPTIONAL, -- Cond RTIReq
	gnss-DataBitAssistanceReq		GNSS-DataBitAssistanceReq		OPTIONAL, -- Cond DataBitsReq
	gnss-AcquisitionAssistanceReq	GNSS-AcquisitionAssistanceReq	OPTIONAL, -- Cond AcquAssistReq
	gnss-AlmanacReq					GNSS-AlmanacReq					OPTIONAL, -- Cond AlmanacReq
	gnss-UTCModelReq				GNSS-UTC-ModelReq				OPTIONAL, -- Cond UTCModReq
	gnss-AuxiliaryInformationReq	GNSS-AuxiliaryInformationReq	OPTIONAL, -- Cond AuxInfoReq
	...,
	[[
		bds-DifferentialCorrectionsReq-r12	
										BDS-DifferentialCorrectionsReq-r12
																			OPTIONAL,	-- Cond DBDS-Req
				bds-GridModelReq-r12		BDS-GridModelReq-r12			OPTIONAL	-- Cond BDS-GridModReq
	]],
	[[
		gnss-RTK-ObservationsReq-r15
									GNSS-RTK-ObservationsReq-r15	OPTIONAL,	-- Cond RTK-OSR-Req
		glo-RTK-BiasInformationReq-r15	
									GLO-RTK-BiasInformationReq-r15	OPTIONAL,	-- Cond GLO-CPB-Req
		gnss-RTK-MAC-CorrectionDifferencesReq-r15
									GNSS-RTK-MAC-CorrectionDifferencesReq-r15
																	OPTIONAL,	-- Cond MAC-Req
		gnss-RTK-ResidualsReq-r15	GNSS-RTK-ResidualsReq-r15		OPTIONAL,	-- Cond Res-Req
		gnss-RTK-FKP-GradientsReq-r15
									GNSS-RTK-FKP-GradientsReq-r15	OPTIONAL,	-- Cond FKP-Req
		gnss-SSR-OrbitCorrectionsReq-r15
									GNSS-SSR-OrbitCorrectionsReq-r15
																	OPTIONAL, 	-- Cond OC-Req
		gnss-SSR-ClockCorrectionsReq-r15
									GNSS-SSR-ClockCorrectionsReq-r15
																	OPTIONAL, 	-- Cond CC-Req
		gnss-SSR-CodeBiasReq-r15	GNSS-SSR-CodeBiasReq-r15		OPTIONAL 	-- Cond CB-Req
	]],
	[[
		gnss-SSR-URA-Req-r16		GNSS-SSR-URA-Req-r16			OPTIONAL,	-- Cond URA-Req
		gnss-SSR-PhaseBiasReq-r16	GNSS-SSR-PhaseBiasReq-r16		OPTIONAL,	-- Cond PB-Req
		gnss-SSR-STEC-CorrectionReq-r16
									GNSS-SSR-STEC-CorrectionReq-r16	OPTIONAL,	-- Cond STEC-Req
		gnss-SSR-GriddedCorrectionReq-r16	GNSS-SSR-GriddedCorrectionReq-r16
																	OPTIONAL,	-- Cond Grid-Req
		navic-DifferentialCorrectionsReq-r16	
										NavIC-DifferentialCorrectionsReq-r16
																		OPTIONAL,	-- Cond DNavIC-Req
				navic-GridModelReq-r16		NavIC-GridModelReq-r16		OPTIONAL	-- Cond NavIC-GridModReq
	]]
}
