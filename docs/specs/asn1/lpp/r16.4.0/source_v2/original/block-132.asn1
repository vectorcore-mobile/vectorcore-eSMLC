GNSS-Almanac ::= SEQUENCE {
	weekNumber					INTEGER (0..255)	OPTIONAL,	-- Need ON
	toa							INTEGER (0..255)	OPTIONAL,	-- Need ON
	ioda						INTEGER (0..3)		OPTIONAL,	-- Need ON
	completeAlmanacProvided		BOOLEAN,
	gnss-AlmanacList			GNSS-AlmanacList,
	...,
	[[	toa-ext-v1240			INTEGER (256..1023)	OPTIONAL,	-- Need ON
		ioda-ext-v1240			INTEGER (4..15)		OPTIONAL	-- Need ON
	]],
	[[
		weekNumber-ext-r16		INTEGER (256..8191)			OPTIONAL,	-- Need ON
		toa-ext2-r16			INTEGER (256..65535)		OPTIONAL	-- Need ON
	]]
}
GNSS-AlmanacList ::= SEQUENCE (SIZE(1..64)) OF GNSS-AlmanacElement
GNSS-AlmanacElement ::= CHOICE {
	keplerianAlmanacSet				AlmanacKeplerianSet,		-- Model-1
	keplerianNAV-Almanac			AlmanacNAV-KeplerianSet,	-- Model-2
	keplerianReducedAlmanac			AlmanacReducedKeplerianSet,	-- Model-3
	keplerianMidiAlmanac			AlmanacMidiAlmanacSet,		-- Model-4
	keplerianGLONASS				AlmanacGLONASS-AlmanacSet,	-- Model-5
	ecef-SBAS-Almanac				AlmanacECEF-SBAS-AlmanacSet,-- Model-6
	...,
	keplerianBDS-Almanac-r12		AlmanacBDS-AlmanacSet-r12,	-- Model-7
	keplerianNavIC-Almanac-r16		AlmanacNavIC-AlmanacSet-r16	-- Model-8
}
