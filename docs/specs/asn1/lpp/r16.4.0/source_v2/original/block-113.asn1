StandardClockModelList ::= SEQUENCE (SIZE(1..2)) OF StandardClockModelElement
StandardClockModelElement ::= SEQUENCE {
	stanClockToc			INTEGER (0..16383),
	stanClockAF2			INTEGER (-32..31),
	stanClockAF1			INTEGER (-1048576..1048575),
	stanClockAF0			INTEGER (-1073741824..1073741823),
	stanClockTgd			INTEGER (-512..511)				OPTIONAL,	-- Need ON
	sisa					INTEGER (0..255),
	stanModelID				INTEGER (0..1)					OPTIONAL,	-- Need ON
	...
}
