NR-DL-PRS-QCL-ProcessingCapability-r16 ::= SEQUENCE {
	dl-PRS-QCL-ProcessingCapabilityBandList-r16			SEQUENCE (SIZE (1..nrMaxBands-r16)) OF
														DL-PRS-QCL-ProcessingCapabilityPerBand-r16,
	...
}
DL-PRS-QCL-ProcessingCapabilityPerBand-r16 ::= SEQUENCE {
	freqBandIndicatorNR-r16						FreqBandIndicatorNR-r16,
	ssb-FromNeighCellAsQCL-r16					ENUMERATED { supported}	OPTIONAL,
	prs-FromServNeighCellAsQCL-r16				ENUMERATED { supported} OPTIONAL,
	...
}
