WLAN-TargetDeviceErrorCauses-r13 ::= SEQUENCE {
	cause-r13								ENUMERATED {undefined,
														requestedMeasurementsNotAvailable,
														notAllrequestedMeasurementsPossible,
														...
														},
	wlan-AP-RSSI-MeasurementNotPossible-r13				NULL		OPTIONAL,
	wlan-AP-RTT-MeasurementNotPossible-r13				NULL		OPTIONAL,
	...
}
