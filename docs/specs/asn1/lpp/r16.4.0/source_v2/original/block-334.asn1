NR-DL-TDOA-LocationServerErrorCauses-r16 ::= SEQUENCE {
	cause-r16		ENUMERATED	{	undefined,
									assistanceDataNotSupportedByServer,
									assistanceDataSupportedButCurrentlyNotAvailableByServer,
									notProvidedAssistanceDataNotSupportedByServer,
									...
								},
	...
}
