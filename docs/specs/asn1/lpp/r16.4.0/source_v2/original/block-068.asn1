NR-TRP-LocationInfo-r16 ::= SEQUENCE (SIZE (1..nrMaxFreqLayers-r16)) OF
									NR-TRP-LocationInfoPerFreqLayer-r16
NR-TRP-LocationInfoPerFreqLayer-r16 ::= SEQUENCE {
	referencePoint-r16			ReferencePoint-r16				OPTIONAL,	-- Cond NotSameAsPrev
	trp-LocationInfoList-r16	SEQUENCE (SIZE (1..nrMaxTRPsPerFreq-r16)) OF
										TRP-LocationInfoElement-r16,
	...
}
TRP-LocationInfoElement-r16 ::= SEQUENCE {
	dl-PRS-ID-r16					INTEGER (0..255),
	nr-PhysCellID-r16				NR-PhysCellID-r16			OPTIONAL,	-- Need ON
	nr-CellGlobalID-r16				NCGI-r15					OPTIONAL,	-- Need ON
	nr-ARFCN-r16					ARFCN-ValueNR-r15			OPTIONAL,	-- Need ON
	associated-DL-PRS-ID-r16		INTEGER (0..255)			OPTIONAL,
	trp-Location-r16				RelativeLocation-r16					OPTIONAL,	-- Need OP
	trp-DL-PRS-ResourceSets-r16		SEQUENCE (SIZE(1..nrMaxSetsPerTrp-r16)) OF
										DL-PRS-ResourceSets-TRP-Element-r16	OPTIONAL,	-- Need OP
	...
}
DL-PRS-ResourceSets-TRP-Element-r16 ::= SEQUENCE {
	dl-PRS-ResourceSetARP-r16			RelativeLocation-r16				OPTIONAL,	-- Need OP
	dl-PRS-Resource-ARP-List-r16		SEQUENCE (SIZE(1..nrMaxResourcesPerSet-r16)) OF
											DL-PRS-Resource-ARP-Element-r16	OPTIONAL,	-- Need OP
	...
}
DL-PRS-Resource-ARP-Element-r16 ::= SEQUENCE {
	dl-PRS-Resource-ARP-location-r16	RelativeLocation-r16				OPTIONAL,	-- Need OP
	...
}
