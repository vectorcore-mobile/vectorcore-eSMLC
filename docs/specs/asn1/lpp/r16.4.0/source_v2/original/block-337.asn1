NR-DL-AoD-RequestAssistanceData-r16 ::= SEQUENCE {
	nr-PhysCellID-r16				NR-PhysCellID-r16						OPTIONAL,
	nr-AdType-r16					BIT STRING { 	dl-prs 	(0),
													posCalc (1) } (SIZE (1..8)),
	...
}
