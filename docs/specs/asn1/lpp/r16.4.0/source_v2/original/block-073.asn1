OTDOA-ReferenceCellInfo ::= SEQUENCE {
	physCellId					INTEGER (0..503),
	cellGlobalId				ECGI						OPTIONAL,		-- Need ON
	earfcnRef					ARFCN-ValueEUTRA			OPTIONAL,		-- Cond NotSameAsServ0
	antennaPortConfig			ENUMERATED {ports1-or-2, ports4, ... }
															OPTIONAL,		-- Cond NotSameAsServ1
	cpLength					ENUMERATED { normal, extended, ... },
	prsInfo						PRS-Info					OPTIONAL,		-- Cond PRS
	...,
	[[ earfcnRef-v9a0			ARFCN-ValueEUTRA-v9a0		OPTIONAL		-- Cond NotSameAsServ2
	]],
	[[	tpId-r14				INTEGER (0..4095)			OPTIONAL,		-- Need ON
		cpLengthCRS-r14			ENUMERATED { normal, extended, ... }	
															OPTIONAL,		-- Cond CRS
		sameMBSFNconfigRef-r14	BOOLEAN						OPTIONAL,		-- Need ON
		dlBandwidth-r14			ENUMERATED {n6, n15, n25, n50, n75, n100}
															OPTIONAL,		-- Cond NotSameAsServ3
		addPRSconfigRef-r14		SEQUENCE (SIZE (1..maxAddPRSconfig-r14)) OF PRS-Info
															OPTIONAL		-- Need ON	
	]],
	[[
		nr-LTE-SFN-Offset-r15	INTEGER (0..1023)			OPTIONAL		-- Cond NR
	]],
	[[
		tdd-config-v1520					TDD-Config-v1520	OPTIONAL,		-- Need ON
		nr-LTE-fineTiming-Offset-r15		INTEGER (0..19)		OPTIONAL		-- Cond FineOffset
	]]
}
maxAddPRSconfig-r14			INTEGER ::= 2
