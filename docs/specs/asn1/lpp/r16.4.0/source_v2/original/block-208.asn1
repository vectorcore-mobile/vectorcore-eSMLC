GNSS-CommonAssistanceDataSupport ::= SEQUENCE {
	gnss-ReferenceTimeSupport				GNSS-ReferenceTimeSupport				
																OPTIONAL, -- Cond RefTimeSup
	gnss-ReferenceLocationSupport			GNSS-ReferenceLocationSupport			
																OPTIONAL, -- Cond RefLocSup
	gnss-IonosphericModelSupport			GNSS-IonosphericModelSupport				
																OPTIONAL, -- Cond IonoModSup
	gnss-EarthOrientationParametersSupport	GNSS-EarthOrientationParametersSupport	
																OPTIONAL, -- Cond EOPSup
	...,
	[[
		gnss-RTK-ReferenceStationInfoSupport-r15	
											GNSS-RTK-ReferenceStationInfoSupport-r15
																OPTIONAL, -- Cond ARPSup
		gnss-RTK-AuxiliaryStationDataSupport-r15
											GNSS-RTK-AuxiliaryStationDataSupport-r15
																OPTIONAL -- Cond AuxARPSup
	]]
}
