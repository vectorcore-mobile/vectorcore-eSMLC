NavIC-DifferentialCorrections-r16 ::= SEQUENCE {
	navic-RefTOWC-r16				INTEGER (0..50400),
	navic-CorrectionListAutoNav-r16	NavIC-CorrectionListAutoNav-r16,
	...
}
NavIC-CorrectionListAutoNav-r16 ::= SEQUENCE (SIZE (1..64)) OF NavIC-CorrectionElementAutoNav-r16
NavIC-CorrectionElementAutoNav-r16 ::= SEQUENCE {
	svID						SV-ID,
	navic-Tod-r16				INTEGER (0..65535),
	navic-iodec-r16				INTEGER (0..255),
	navic-UDRAI-r16				INTEGER (-16..15),
	navic-UDRArateI-r16			INTEGER (-16..15),
	navic-EDC-r16				NavIC-EDC-r16,
	navic-CDC-r16				NavIC-CDC-r16,
	...
}
NavIC-EDC-r16 ::= SEQUENCE {
	navic-AlphaEDC-r16				INTEGER (-8192..8191),
	navic-BetaEDC-r16				INTEGER (-8192..8191),
	navic-GammaEDC-r16				INTEGER (-16384..16383),
	navic-AoIcorrection-r16			INTEGER (-2048..2047),
	navic-AoRAcorrection-r16		INTEGER (-2048..2047),
	navic-SemiMajorcorrection-r16	INTEGER (-2048..2047),
	...
}
NavIC-CDC-r16 ::= SEQUENCE {
	navic-ClockBiasCorrection-r16	INTEGER (-4096..4095),
	navic-ClockDriftCorrection-r16	INTEGER (-128..127),
	...
}
