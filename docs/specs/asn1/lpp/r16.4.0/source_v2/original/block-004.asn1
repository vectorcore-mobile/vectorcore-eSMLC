LPP-TransactionID ::= SEQUENCE {
	initiator				Initiator,
	transactionNumber		TransactionNumber,
	...
}
Initiator ::= ENUMERATED {
	locationServer,
	targetDevice,
	...
}
TransactionNumber ::= INTEGER (0..255)
