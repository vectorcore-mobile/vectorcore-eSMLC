GNSS-RTK-ReferenceStationInfo-r15 ::= SEQUENCE {
	referenceStationID-r15					GNSS-ReferenceStationID-r15,
	referenceStationIndicator-r15			ENUMERATED {physical, non-physical},
	antenna-reference-point-ECEF-X-r15		INTEGER (-137438953472..137438953471),
	antenna-reference-point-ECEF-Y-r15		INTEGER (-137438953472..137438953471),
	antenna-reference-point-ECEF-Z-r15		INTEGER (-137438953472..137438953471),
	antennaHeight-r15						INTEGER (0..65535)					OPTIONAL, -- Need ON
	antennaDescription-r15					AntennaDescription-r15				OPTIONAL, -- Need ON
	antenna-reference-point-unc-r15			AntennaReferencePointUnc-r15		OPTIONAL, -- Need ON
	physical-reference-station-info-r15		PhysicalReferenceStationInfo-r15	OPTIONAL, -- Cond NP
	...,
	[[
	equalIntegerAmbiguityLevel-r16			EqualIntegerAmbiguityLevel-r16		OPTIONAL -- Need ON
	]]
}
AntennaDescription-r15 ::= SEQUENCE {
	antennaDescriptor-r15					VisibleString (SIZE (1..256)),
	antennaSetUpID-r15						ENUMERATED { non-zero }				OPTIONAL, -- Need OP
	...
}
AntennaReferencePointUnc-r15 ::= SEQUENCE {
	uncertainty-X-r15						INTEGER (0..255),
	confidence-X-r15						INTEGER (0..100),
	uncertainty-Y-r15						INTEGER (0..255),
	confidence-Y-r15						INTEGER (0..100),
	uncertainty-Z-r15						INTEGER (0..255),
	confidence-Z-r15						INTEGER (0..100),
	...
}
PhysicalReferenceStationInfo-r15 ::= SEQUENCE {
	physicalReferenceStationID-r15			GNSS-ReferenceStationID-r15,
	physical-ARP-ECEF-X-r15					INTEGER (-137438953472..137438953471),
	physical-ARP-ECEF-Y-r15					INTEGER (-137438953472..137438953471),
	physical-ARP-ECEF-Z-r15					INTEGER (-137438953472..137438953471),
	physical-ARP-unc-r15					AntennaReferencePointUnc-r15		OPTIONAL, -- Need ON
	...
}
EqualIntegerAmbiguityLevel-r16 ::= CHOICE {
	allReferenceStations-r16				NULL,
	referenceStationList-r16				ReferenceStationList-r16
}
ReferenceStationList-r16 ::= SEQUENCE (SIZE(1..16)) OF GNSS-ReferenceStationID-r15
