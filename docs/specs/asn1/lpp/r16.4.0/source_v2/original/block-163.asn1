NavIC-GridModelParameter-r16 ::= SEQUENCE {
			navic-RefTOWC-r16	INTEGER (0..50400),
			regionMasked-r16	INTEGER (0..1023),
			regionIgpList-r16	RegionIgpList-r16,
			...
		}
		
		RegionIgpList-r16 ::= SEQUENCE (SIZE (1..16)) OF RegionIgpElement-r16
		
		RegionIgpElement-r16 ::= SEQUENCE {
			regionID-r16	INTEGER (0..15),
			givei1-r16		INTEGER (0..15),
			givd1-r16		INTEGER (0..511),
			givei2-r16		INTEGER (0..15),
			givd2-r16		INTEGER (0..511),
			givei3-r16		INTEGER (0..15),
			givd3-r16		INTEGER (0..511),
			givei4-r16		INTEGER (0..15),
			givd4-r16		INTEGER (0..511),
			givei5-r16		INTEGER (0..15),
			givd5-r16		INTEGER (0..511),
			givei6-r16		INTEGER (0..15),
			givd6-r16		INTEGER (0..511),
			givei7-r16		INTEGER (0..15),
			givd7-r16		INTEGER (0..511),
			givei8-r16		INTEGER (0..15),
			givd8-r16		INTEGER (0..511),
			givei9-r16		INTEGER (0..15),
			givd9-r16		INTEGER (0..511),
			givei10-r16		INTEGER (0..15),
			givd10-r16		INTEGER (0..511),
			givei11-r16		INTEGER (0..15),
			givd11-r16		INTEGER (0..511),
			givei12-r16		INTEGER (0..15),
			givd12-r16		INTEGER (0..511),
			givei13-r16		INTEGER (0..15),
			givd13-r16		INTEGER (0..511),
			givei14-r16		INTEGER (0..15),
			givd14-r16		INTEGER (0..511),
			givei15-r16		INTEGER (0..15),
			givd15-r16		INTEGER (0..511),
			...
		}
